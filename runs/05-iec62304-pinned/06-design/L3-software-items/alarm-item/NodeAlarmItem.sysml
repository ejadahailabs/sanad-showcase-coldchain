// NodeAlarmItem — node `alarm-item` (level 3, software-item, IEC 62304 class C); satisfies ONLY its own 4 requirements. Generated by tools/pinned_model.py — edit there. RUN-05.
private import ScalarValues::*;
private import ProjectRequirements::*;
private import MrtmInterfaces::*;
private import LevelPorts::*;
private import MrtmSoftware::*;
private import SoftwareProfile::*;

package NodeAlarmItem {

    doc /* LEVEL 3 — SOFTWARE ITEM `alarm-item` (IEC 62304 §5.3; class C). */

    #Service part def AlarmSwItem :> AlarmItem {
        doc /* IEC 62304 software item, class C. Units: alarm-mgr. */
        port excursion : ~ExcursionFlow;
        port alarmState : AlarmStateFlow;
        port records : RecordFlow;
        port powerEvents : ~PowerEventFlow;
        port heartbeat : HeartbeatFlow;
        port buzzerDrive : GpioOutPort;
        port lightDrive : GpioOutPort;
        port button : GpioInPort;
    }
    part alarmSwItem : AlarmSwItem;

    satisfy 'MRTM-ALI-001' by alarmSwItem;
    satisfy 'MRTM-ALI-002' by alarmSwItem;
    satisfy 'MRTM-ALI-003' by alarmSwItem;
    satisfy 'MRTM-ALI-004' by alarmSwItem;
}
