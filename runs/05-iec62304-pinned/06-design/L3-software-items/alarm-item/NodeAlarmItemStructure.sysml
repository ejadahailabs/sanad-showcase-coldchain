// NodeAlarmItemStructure — internal structure of item `alarm-item` (view package, no satisfy). Generated by tools/pinned_model.py — edit there. RUN-05.
private import ScalarValues::*;
private import MrtmInterfaces::*;
private import LevelPorts::*;
private import MrtmSoftware::*;
private import NodeAlarmMgr::*;

package NodeAlarmItemStructure {

    doc /* Inside item alarm-item: its units, and the neighbours its boundary ports meet (each shown by the shared ports only). */
    part alarmMgr : AlarmMgrUnit;
    part excursionItem { port excursion : ExcursionFlow; }  // neighbour, shared ports only
    part displayItem { port alarmState : ~AlarmStateFlow; }  // neighbour, shared ports only
    part logItem { port records : ~RecordFlow; }  // neighbour, shared ports only
    part powerItem { port events : PowerEventFlow; }  // neighbour, shared ports only
    part supervisorItem { port heartbeat : ~HeartbeatFlow; }  // neighbour, shared ports only
    part hardwareItem { port buzzerDrive : ~GpioOutPort; port lightDrive : ~GpioOutPort; port button : ~GpioInPort; }  // neighbour, shared ports only
    connect excursionItem.excursion to alarmMgr.excursion;
    connect alarmMgr.alarm to displayItem.alarmState;
    connect alarmMgr.log to logItem.records;
    connect powerItem.events to alarmMgr.powerEvents;
    connect alarmMgr.heartbeat to supervisorItem.heartbeat;
    connect alarmMgr.buzzerDrive to hardwareItem.buzzerDrive;
    connect alarmMgr.lightDrive to hardwareItem.lightDrive;
    connect hardwareItem.button to alarmMgr.button;
}
