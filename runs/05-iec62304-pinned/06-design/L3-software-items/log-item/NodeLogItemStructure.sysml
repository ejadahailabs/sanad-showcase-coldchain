// NodeLogItemStructure — internal structure of item `log-item` (view package, no satisfy). Generated by tools/pinned_model.py — edit there. RUN-05.
private import ScalarValues::*;
private import MrtmInterfaces::*;
private import LevelPorts::*;
private import MrtmSoftware::*;
private import NodeEventLog::*;
private import NodeHistoryRing::*;
private import NodeRtcClock::*;

package NodeLogItemStructure {

    doc /* Inside item log-item: its units, and the neighbours its boundary ports meet (each shown by the shared ports only). */
    part eventLog : EventLogUnit;
    part historyRing : HistoryRingUnit;
    part rtcClock : RtcClockUnit;
    part alarmItem { port records : RecordFlow; }  // neighbour, shared ports only
    part powerItem { port records : RecordFlow; }  // neighbour, shared ports only
    part supervisorItem { port records : RecordFlow; }  // neighbour, shared ports only
    part usbItem { port history : ~HistoryFlow; }  // neighbour, shared ports only
    part hardwareItem { port clockBus : ~I2cPort; }  // neighbour, shared ports only
    connect alarmItem.records to eventLog.records;
    connect powerItem.records to eventLog.records;
    connect supervisorItem.records to eventLog.records;
    connect eventLog.toRing to historyRing.append;
    connect rtcClock.now to eventLog.clock;
    connect rtcClock.i2c to hardwareItem.clockBus;
    connect historyRing.history to usbItem.history;
}
