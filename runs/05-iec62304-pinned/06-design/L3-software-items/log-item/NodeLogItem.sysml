// NodeLogItem — node `log-item` (level 3, software-item, IEC 62304 class C); satisfies ONLY its own 3 requirements. Generated by tools/pinned_model.py — edit there. RUN-05.
private import ScalarValues::*;
private import ProjectRequirements::*;
private import MrtmInterfaces::*;
private import LevelPorts::*;
private import MrtmSoftware::*;
private import SoftwareProfile::*;

package NodeLogItem {

    doc /* LEVEL 3 — SOFTWARE ITEM `log-item` (IEC 62304 §5.3; class C). */

    #Service part def LogSwItem :> LogItem {
        doc /* IEC 62304 software item, class C. Units: event-log, history-ring, rtc-clock. */
        port records : ~RecordFlow;
        port clock : I2cPort;
        port history : HistoryFlow;
    }
    part logSwItem : LogSwItem;

    satisfy 'MRTM-LGI-001' by logSwItem;
    satisfy 'MRTM-LGI-002' by logSwItem;
    satisfy 'MRTM-LGI-003' by logSwItem;
}
