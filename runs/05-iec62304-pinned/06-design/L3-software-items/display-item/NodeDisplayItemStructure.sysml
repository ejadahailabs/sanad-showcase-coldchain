// NodeDisplayItemStructure — internal structure of item `display-item` (view package, no satisfy). Generated by tools/pinned_model.py — edit there. RUN-05.
private import ScalarValues::*;
private import MrtmInterfaces::*;
private import LevelPorts::*;
private import MrtmSoftware::*;
private import NodeDisplayMgr::*;

package NodeDisplayItemStructure {

    doc /* Inside item display-item: its units, and the neighbours its boundary ports meet (each shown by the shared ports only). */
    part displayMgr : DisplayMgrUnit;
    part sensorItem { port samples : SampleFlow; }  // neighbour, shared ports only
    part alarmItem { port alarmState : AlarmStateFlow; }  // neighbour, shared ports only
    part hardwareItem { port displayBus : ~I2cPort; }  // neighbour, shared ports only
    connect sensorItem.samples to displayMgr.samples;
    connect alarmItem.alarmState to displayMgr.alarm;
    connect displayMgr.i2c to hardwareItem.displayBus;
}
