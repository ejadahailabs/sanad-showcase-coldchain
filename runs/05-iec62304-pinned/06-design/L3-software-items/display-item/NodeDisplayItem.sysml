// NodeDisplayItem — node `display-item` (level 3, software-item, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeDisplayItem {

    doc /* LEVEL 3 — SOFTWARE ITEM `display-item` (IEC 62304 §5.3; class C). */

    #Service part def DisplaySwItem :> DisplayItem {
        doc /* IEC 62304 software item, class C. Units: display-mgr. */
        port samples : ~SampleFlow;
        port alarmState : ~AlarmStateFlow;
        port i2c : I2cPort;
    }
    part displaySwItem : DisplaySwItem;

    satisfy 'MRTM-DSI-001' by displaySwItem;
    satisfy 'MRTM-DSI-002' by displaySwItem;
}
