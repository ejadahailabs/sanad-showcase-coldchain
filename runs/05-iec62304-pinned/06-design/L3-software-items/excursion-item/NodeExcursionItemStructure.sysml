// NodeExcursionItemStructure — internal structure of item `excursion-item` (view package, no satisfy). Generated by tools/pinned_model.py — edit there. RUN-05.
private import ScalarValues::*;
private import MrtmInterfaces::*;
private import LevelPorts::*;
private import MrtmSoftware::*;
private import NodeLimitEvaluator::*;

package NodeExcursionItemStructure {

    doc /* Inside item excursion-item: its units, and the neighbours its boundary ports meet (each shown by the shared ports only). */
    part limitEvaluator : LimitEvaluatorUnit;
    part sensorItem { port samples : SampleFlow; }  // neighbour, shared ports only
    part alarmItem { port excursion : ~ExcursionFlow; }  // neighbour, shared ports only
    part supervisorItem { port band : BandFlow; }  // neighbour, shared ports only
    connect sensorItem.samples to limitEvaluator.samples;
    connect limitEvaluator.excursion to alarmItem.excursion;
    connect supervisorItem.band to limitEvaluator.band;
}
