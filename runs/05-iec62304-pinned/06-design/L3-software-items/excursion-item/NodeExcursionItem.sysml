// NodeExcursionItem — node `excursion-item` (level 3, software-item, IEC 62304 class C); satisfies ONLY its own 3 requirements. Generated by tools/pinned_model.py — edit there. RUN-05.
private import ScalarValues::*;
private import ProjectRequirements::*;
private import MrtmInterfaces::*;
private import LevelPorts::*;
private import MrtmSoftware::*;
private import SoftwareProfile::*;

package NodeExcursionItem {

    doc /* LEVEL 3 — SOFTWARE ITEM `excursion-item` (IEC 62304 §5.3; class C). */

    #Service part def ExcursionSwItem :> ExcursionItem {
        doc /* IEC 62304 software item, class C. Units: limit-evaluator. */
        port samples : ~SampleFlow;
        port excursion : ExcursionFlow;
        port band : ~BandFlow;
    }
    part excursionSwItem : ExcursionSwItem;

    satisfy 'MRTM-EXI-001' by excursionSwItem;
    satisfy 'MRTM-EXI-002' by excursionSwItem;
    satisfy 'MRTM-EXI-003' by excursionSwItem;
}
