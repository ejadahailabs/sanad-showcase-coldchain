// NodeSupervisorItem — node `supervisor-item` (level 3, software-item, IEC 62304 class C); satisfies ONLY its own 3 requirements. Generated by tools/pinned_model.py — edit there. RUN-05.
private import ScalarValues::*;
private import ProjectRequirements::*;
private import MrtmInterfaces::*;
private import LevelPorts::*;
private import MrtmSoftware::*;
private import SoftwareProfile::*;

package NodeSupervisorItem {

    doc /* LEVEL 3 — SOFTWARE ITEM `supervisor-item` (IEC 62304 §5.3; class C). */

    #Service part def SupervisorSwItem :> SupervisorItem {
        doc /* IEC 62304 software item, class C. Units: wdt-kicker, diagnostics, config-mgr. */
        port heartbeat : ~HeartbeatFlow;
        port pulses : GpioOutPort;
        port records : RecordFlow;
        port band : BandFlow;
    }
    part supervisorSwItem : SupervisorSwItem;

    satisfy 'MRTM-SVI-001' by supervisorSwItem;
    satisfy 'MRTM-SVI-002' by supervisorSwItem;
    satisfy 'MRTM-SVI-003' by supervisorSwItem;
}
