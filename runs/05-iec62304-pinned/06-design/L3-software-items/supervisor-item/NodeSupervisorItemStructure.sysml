// NodeSupervisorItemStructure — internal structure of item `supervisor-item` (view package, no satisfy). Generated by tools/pinned_model.py — edit there. RUN-05.
private import ScalarValues::*;
private import MrtmInterfaces::*;
private import LevelPorts::*;
private import MrtmSoftware::*;
private import NodeWdtKicker::*;
private import NodeDiagnostics::*;
private import NodeConfigMgr::*;

package NodeSupervisorItemStructure {

    doc /* Inside item supervisor-item: its units, and the neighbours its boundary ports meet (each shown by the shared ports only). */
    part wdtKicker : WdtKickerUnit;
    part diagnostics : DiagnosticsUnit;
    part configMgr : ConfigMgrUnit;
    part alarmItem { port heartbeat : HeartbeatFlow; }  // neighbour, shared ports only
    part hardwareItem { port kick : ~GpioOutPort; }  // neighbour, shared ports only
    part logItem { port records : ~RecordFlow; }  // neighbour, shared ports only
    part excursionItem { port band : ~BandFlow; }  // neighbour, shared ports only
    connect alarmItem.heartbeat to wdtKicker.heartbeat;
    connect wdtKicker.pulses to hardwareItem.kick;
    connect diagnostics.log to logItem.records;
    connect configMgr.band to excursionItem.band;
}
