// NodeUsbItemStructure — internal structure of item `usb-item` (view package, no satisfy). Generated by tools/pinned_model.py — edit there. RUN-05.
private import ScalarValues::*;
private import MrtmInterfaces::*;
private import LevelPorts::*;
private import MrtmSoftware::*;
private import NodeUsbExport::*;

package NodeUsbItemStructure {

    doc /* Inside item usb-item: its units, and the neighbours its boundary ports meet (each shown by the shared ports only). */
    part usbExport : UsbExportUnit;
    part logItem { port history : HistoryFlow; }  // neighbour, shared ports only
    part hardwareItem { port usbData : ~UsbPort; }  // neighbour, shared ports only
    connect logItem.history to usbExport.history;
    connect usbExport.usb to hardwareItem.usbData;
}
