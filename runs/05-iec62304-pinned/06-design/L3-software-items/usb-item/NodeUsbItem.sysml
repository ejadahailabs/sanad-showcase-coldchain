// NodeUsbItem — node `usb-item` (level 3, software-item, IEC 62304 class B); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeUsbItem {

    doc /* LEVEL 3 — SOFTWARE ITEM `usb-item` (IEC 62304 §5.3; class B). */

    #Service part def UsbSwItem :> UsbItem {
        doc /* IEC 62304 software item, class B. Segregation (§5.3.5): ADR-0034 / A-48: own lowest-priority task on core 0, read-only accessor, owns no data another item reads, task watchdog, CRC-32 per record. Units: usb-export. */
        port history : ~HistoryFlow;
        port usb : UsbPort;
    }
    part usbSwItem : UsbSwItem;

    satisfy 'MRTM-USI-001' by usbSwItem;
    satisfy 'MRTM-USI-002' by usbSwItem;
}
