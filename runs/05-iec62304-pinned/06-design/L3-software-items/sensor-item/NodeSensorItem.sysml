// NodeSensorItem — node `sensor-item` (level 3, software-item, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeSensorItem {

    doc /* LEVEL 3 — SOFTWARE ITEM `sensor-item` (IEC 62304 §5.3; class C). */

    #Service part def SensorSwItem :> SensorItem {
        doc /* IEC 62304 software item, class C. Units: sensor-sampler. */
        port bus : OneWirePort;
        port samples : SampleFlow;
    }
    part sensorSwItem : SensorSwItem;

    satisfy 'MRTM-SNI-001' by sensorSwItem;
    satisfy 'MRTM-SNI-002' by sensorSwItem;
}
