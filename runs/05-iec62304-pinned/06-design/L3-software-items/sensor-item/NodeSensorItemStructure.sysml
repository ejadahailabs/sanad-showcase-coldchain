// NodeSensorItemStructure — internal structure of item `sensor-item` (view package, no satisfy). Generated by tools/pinned_model.py — edit there. RUN-05.
private import ScalarValues::*;
private import MrtmInterfaces::*;
private import LevelPorts::*;
private import MrtmSoftware::*;
private import NodeSensorSampler::*;

package NodeSensorItemStructure {

    doc /* Inside item sensor-item: its units, and the neighbours its boundary ports meet (each shown by the shared ports only). */
    part sensorSampler : SensorSamplerUnit;
    part hardwareItem { port probeBus : ~OneWirePort; }  // neighbour, shared ports only
    part excursionItem { port samples : ~SampleFlow; }  // neighbour, shared ports only
    part displayItem { port samples : ~SampleFlow; }  // neighbour, shared ports only
    connect sensorSampler.bus to hardwareItem.probeBus;
    connect sensorSampler.samples to excursionItem.samples;
    connect sensorSampler.samples to displayItem.samples;
}
