// NodePowerItem — node `power-item` (level 3, software-item, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodePowerItem {

    doc /* LEVEL 3 — SOFTWARE ITEM `power-item` (IEC 62304 §5.3; class C). */

    #Service part def PowerSwItem :> PowerItem {
        doc /* IEC 62304 software item, class C. Units: power-mon. */
        port mainsSense : GpioInPort;
        port batterySense : ~PowerPort;
        port events : PowerEventFlow;
        port records : RecordFlow;
    }
    part powerSwItem : PowerSwItem;

    satisfy 'MRTM-PWI-001' by powerSwItem;
    satisfy 'MRTM-PWI-002' by powerSwItem;
}
