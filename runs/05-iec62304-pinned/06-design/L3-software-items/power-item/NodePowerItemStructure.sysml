// NodePowerItemStructure — internal structure of item `power-item` (view package, no satisfy). Generated by tools/pinned_model.py — edit there. RUN-05.
private import ScalarValues::*;
private import MrtmInterfaces::*;
private import LevelPorts::*;
private import MrtmSoftware::*;
private import NodePowerMon::*;

package NodePowerItemStructure {

    doc /* Inside item power-item: its units, and the neighbours its boundary ports meet (each shown by the shared ports only). */
    part powerMon : PowerMonUnit;
    part hardwareItem { port mainsSense : ~GpioInPort; port batterySense : PowerPort; }  // neighbour, shared ports only
    part alarmItem { port powerEvents : ~PowerEventFlow; }  // neighbour, shared ports only
    part logItem { port records : ~RecordFlow; }  // neighbour, shared ports only
    connect hardwareItem.mainsSense to powerMon.mainsSense;
    connect hardwareItem.batterySense to powerMon.batterySense;
    connect powerMon.events to alarmItem.powerEvents;
    connect powerMon.log to logItem.records;
}
