// NodeDiagnostics — node `diagnostics` (level 4, software-unit, IEC 62304 class C); satisfies ONLY its own 1 requirements. Generated by tools/pinned_model.py — edit there. RUN-05.
private import ScalarValues::*;
private import ProjectRequirements::*;
private import MrtmInterfaces::*;
private import LevelPorts::*;
private import MrtmSoftware::*;
private import SoftwareProfile::*;

package NodeDiagnostics {

    doc /* LEVEL 4 — SOFTWARE UNIT `diagnostics` (IEC 62304 §5.4/§5.5; class C). */

    #Component part def DiagnosticsUnit :> Diagnostics {
        doc /* IEC 62304 software unit (§5.4.1), class C (its item `supervisor-item`). Code: 10-src/firmware/components/diagnostics/. Contract (§5.4.2/§5.4.3): MrtmSwDetail::DiagnosticsApi and contracts.md. */
    }
    part diagnosticsUnit : DiagnosticsUnit;

    satisfy 'MRTM-DGN-001' by diagnosticsUnit;
}
