// NodeEventLog — node `event-log` (level 4, software-unit, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeEventLog {

    doc /* LEVEL 4 — SOFTWARE UNIT `event-log` (IEC 62304 §5.4/§5.5; class C). */

    #Component part def EventLogUnit :> EventLog {
        doc /* IEC 62304 software unit (§5.4.1), class C (its item `log-item`). Code: 10-src/firmware/components/event_log/. Contract (§5.4.2/§5.4.3): MrtmSwDetail::EventLogApi and contracts.md. */
        port toRing : RecordFlow;
        port clock : ~TimeFlow;
    }
    part eventLogUnit : EventLogUnit;

    satisfy 'MRTM-EVL-001' by eventLogUnit;
    satisfy 'MRTM-EVL-002' by eventLogUnit;
}
