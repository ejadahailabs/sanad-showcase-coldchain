// NodeHistoryRing — node `history-ring` (level 4, software-unit, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeHistoryRing {

    doc /* LEVEL 4 — SOFTWARE UNIT `history-ring` (IEC 62304 §5.4/§5.5; class C). */

    #Component part def HistoryRingUnit :> HistoryRingStore {
        doc /* IEC 62304 software unit (§5.4.1), class C (its item `log-item`). Code: 10-src/firmware/components/history_ring/. Contract (§5.4.2/§5.4.3): MrtmSwDetail::HistoryRingApi and contracts.md. */
        port append : ~RecordFlow;
        port history : HistoryFlow;
    }
    part historyRingUnit : HistoryRingUnit;

    satisfy 'MRTM-HRG-001' by historyRingUnit;
    satisfy 'MRTM-HRG-002' by historyRingUnit;
}
