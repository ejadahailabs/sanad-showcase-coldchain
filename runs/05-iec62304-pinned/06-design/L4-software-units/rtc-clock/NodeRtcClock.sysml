// NodeRtcClock — node `rtc-clock` (level 4, software-unit, IEC 62304 class C); satisfies ONLY its own 1 requirements. Generated by tools/pinned_model.py — edit there. RUN-05.
private import ScalarValues::*;
private import ProjectRequirements::*;
private import MrtmInterfaces::*;
private import LevelPorts::*;
private import MrtmSoftware::*;
private import SoftwareProfile::*;

package NodeRtcClock {

    doc /* LEVEL 4 — SOFTWARE UNIT `rtc-clock` (IEC 62304 §5.4/§5.5; class C). */

    #Component part def RtcClockUnit :> RtcClock {
        doc /* IEC 62304 software unit (§5.4.1), class C (its item `log-item`). Code: 10-src/firmware/components/rtc_clock/. Contract (§5.4.2/§5.4.3): MrtmSwDetail::RtcClockApi and contracts.md. */
        port i2c : I2cPort;
        port now : TimeFlow;
    }
    part rtcClockUnit : RtcClockUnit;

    satisfy 'MRTM-RTK-001' by rtcClockUnit;
}
