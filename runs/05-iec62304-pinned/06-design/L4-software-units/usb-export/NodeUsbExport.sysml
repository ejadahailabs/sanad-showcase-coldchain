// NodeUsbExport — node `usb-export` (level 4, software-unit, IEC 62304 class B); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeUsbExport {

    doc /* LEVEL 4 — SOFTWARE UNIT `usb-export` (IEC 62304 §5.4/§5.5; class B). */

    #Component part def UsbExportUnit :> UsbExport {
        doc /* IEC 62304 software unit (§5.4.1), class B (its item `usb-item`). Code: 10-src/firmware/components/usb_export/. Contract (§5.4.2/§5.4.3): MrtmSwDetail::UsbExportApi and contracts.md. */
        port history : ~HistoryFlow;
        port usb : UsbPort;
    }
    part usbExportUnit : UsbExportUnit;

    satisfy 'MRTM-UXP-001' by usbExportUnit;
    satisfy 'MRTM-UXP-002' by usbExportUnit;
}
