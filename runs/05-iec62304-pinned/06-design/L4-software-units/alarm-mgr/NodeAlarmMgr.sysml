// NodeAlarmMgr — node `alarm-mgr` (level 4, software-unit, IEC 62304 class C); satisfies ONLY its own 4 requirements. Generated by tools/pinned_model.py — edit there. RUN-05.
private import ScalarValues::*;
private import ProjectRequirements::*;
private import MrtmInterfaces::*;
private import LevelPorts::*;
private import MrtmSoftware::*;
private import SoftwareProfile::*;

package NodeAlarmMgr {

    doc /* LEVEL 4 — SOFTWARE UNIT `alarm-mgr` (IEC 62304 §5.4/§5.5; class C). */

    #Component part def AlarmMgrUnit :> AlarmMgr {
        doc /* IEC 62304 software unit (§5.4.1), class C (its item `alarm-item`). Code: 10-src/firmware/components/alarm_mgr/. Contract (§5.4.2/§5.4.3): MrtmSwDetail::AlarmMgrApi and contracts.md. */
        port powerEvents : ~PowerEventFlow;
        port buzzerDrive : GpioOutPort;
        port lightDrive : GpioOutPort;
        port button : GpioInPort;
    }
    part alarmMgrUnit : AlarmMgrUnit;

    satisfy 'MRTM-AMG-001' by alarmMgrUnit;
    satisfy 'MRTM-AMG-002' by alarmMgrUnit;
    satisfy 'MRTM-AMG-003' by alarmMgrUnit;
    satisfy 'MRTM-AMG-004' by alarmMgrUnit;
}
