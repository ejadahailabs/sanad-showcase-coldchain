// NodeConfigMgr — node `config-mgr` (level 4, software-unit, IEC 62304 class C); satisfies ONLY its own 1 requirements. Generated by tools/pinned_model.py — edit there. RUN-05.
private import ScalarValues::*;
private import ProjectRequirements::*;
private import MrtmInterfaces::*;
private import LevelPorts::*;
private import MrtmSoftware::*;
private import SoftwareProfile::*;

package NodeConfigMgr {

    doc /* LEVEL 4 — SOFTWARE UNIT `config-mgr` (IEC 62304 §5.4/§5.5; class C). */

    #Component part def ConfigMgrUnit :> ConfigMgr {
        doc /* IEC 62304 software unit (§5.4.1), class C (its item `supervisor-item`). Code: 10-src/firmware/components/config_mgr/. Contract (§5.4.2/§5.4.3): MrtmSwDetail::ConfigMgrApi and contracts.md. */
        port band : BandFlow;
    }
    part configMgrUnit : ConfigMgrUnit;

    satisfy 'MRTM-CFG-001' by configMgrUnit;
}
