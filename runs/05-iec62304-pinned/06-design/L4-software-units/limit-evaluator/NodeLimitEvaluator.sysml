// NodeLimitEvaluator — node `limit-evaluator` (level 4, software-unit, IEC 62304 class C); satisfies ONLY its own 3 requirements. Generated by tools/pinned_model.py — edit there. RUN-05.
private import ScalarValues::*;
private import ProjectRequirements::*;
private import MrtmInterfaces::*;
private import LevelPorts::*;
private import MrtmSoftware::*;
private import SoftwareProfile::*;

package NodeLimitEvaluator {

    doc /* LEVEL 4 — SOFTWARE UNIT `limit-evaluator` (IEC 62304 §5.4/§5.5; class C). */

    #Component part def LimitEvaluatorUnit :> LimitEvaluator {
        doc /* IEC 62304 software unit (§5.4.1), class C (its item `excursion-item`). Code: 10-src/firmware/components/limit_evaluator/. Contract (§5.4.2/§5.4.3): MrtmSwDetail::LimitEvaluatorApi and contracts.md. */
        port band : ~BandFlow;
    }
    part limitEvaluatorUnit : LimitEvaluatorUnit;

    satisfy 'MRTM-LEV-001' by limitEvaluatorUnit;
    satisfy 'MRTM-LEV-002' by limitEvaluatorUnit;
    satisfy 'MRTM-LEV-003' by limitEvaluatorUnit;
}
