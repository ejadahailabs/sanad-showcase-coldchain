// NodePowerMon — node `power-mon` (level 4, software-unit, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodePowerMon {

    doc /* LEVEL 4 — SOFTWARE UNIT `power-mon` (IEC 62304 §5.4/§5.5; class C). */

    #Component part def PowerMonUnit :> PowerMon {
        doc /* IEC 62304 software unit (§5.4.1), class C (its item `power-item`). Code: 10-src/firmware/components/power_mon/. Contract (§5.4.2/§5.4.3): MrtmSwDetail::PowerMonApi and contracts.md. */
        port mainsSense : GpioInPort;
        port batterySense : ~PowerPort;
        port events : PowerEventFlow;
    }
    part powerMonUnit : PowerMonUnit;

    satisfy 'MRTM-PMN-001' by powerMonUnit;
    satisfy 'MRTM-PMN-002' by powerMonUnit;
}
