// NodeSensorSampler — node `sensor-sampler` (level 4, software-unit, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeSensorSampler {

    doc /* LEVEL 4 — SOFTWARE UNIT `sensor-sampler` (IEC 62304 §5.4/§5.5; class C). */

    #Component part def SensorSamplerUnit :> SensorSampler {
        doc /* IEC 62304 software unit (§5.4.1), class C (its item `sensor-item`). Code: 10-src/firmware/components/sensor_sampler/. Contract (§5.4.2/§5.4.3): MrtmSwDetail::SensorSamplerApi and contracts.md. */
        port bus : OneWirePort;
    }
    part sensorSamplerUnit : SensorSamplerUnit;

    satisfy 'MRTM-SMP-001' by sensorSamplerUnit;
    satisfy 'MRTM-SMP-002' by sensorSamplerUnit;
}
