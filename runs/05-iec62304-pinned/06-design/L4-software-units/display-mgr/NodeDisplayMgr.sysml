// NodeDisplayMgr — node `display-mgr` (level 4, software-unit, IEC 62304 class C); satisfies ONLY its own 2 requirements. Generated by tools/pinned_model.py — edit there. RUN-05.
private import ScalarValues::*;
private import ProjectRequirements::*;
private import MrtmInterfaces::*;
private import LevelPorts::*;
private import MrtmSoftware::*;
private import SoftwareProfile::*;

package NodeDisplayMgr {

    doc /* LEVEL 4 — SOFTWARE UNIT `display-mgr` (IEC 62304 §5.4/§5.5; class C). */

    #Component part def DisplayMgrUnit :> DisplayMgr {
        doc /* IEC 62304 software unit (§5.4.1), class C (its item `display-item`). Code: 10-src/firmware/components/display_mgr/. Contract (§5.4.2/§5.4.3): MrtmSwDetail::DisplayMgrApi and contracts.md. */
        port samples : ~SampleFlow;
        port i2c : I2cPort;
    }
    part displayMgrUnit : DisplayMgrUnit;

    satisfy 'MRTM-DMG-001' by displayMgrUnit;
    satisfy 'MRTM-DMG-002' by displayMgrUnit;
}
