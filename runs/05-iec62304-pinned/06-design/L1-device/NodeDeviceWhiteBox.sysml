// NodeDeviceWhiteBox — white box of the device in its context (view package, no satisfy). Generated by tools/pinned_model.py — edit there. RUN-05.
private import ScalarValues::*;
private import MrtmInterfaces::*;
private import LevelPorts::*;
private import MrtmSystemContext::*;
private import NodeHardwareItem::*;
private import NodeSoftwareSystem::*;

package NodeDeviceWhiteBox {

    doc /* Device block: the hardware item and the software system, and the neighbours the device boundary meets. */
    part hardwareItem : HardwareItem;
    part softwareSystem : SoftwareSystem;
    part fridge : Fridge;
    part mains : MainsSupply;
    part usbHost : UsbHost;
    part staff : Staff;
    connect fridge.air to hardwareItem.air;
    connect mains.output to hardwareItem.mains;
    connect hardwareItem.usb to usbHost.usb;
    connect hardwareItem.alarmSignals to staff.alarmSignals;
    connect hardwareItem.screen to staff.screen;
    connect softwareSystem.hal to hardwareItem.hal;
}
