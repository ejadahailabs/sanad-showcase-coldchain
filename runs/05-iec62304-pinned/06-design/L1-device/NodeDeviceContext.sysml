// NodeDeviceContext — the device and its neighbours (view package, no satisfy). Generated by tools/pinned_model.py — edit there. RUN-05.
private import ScalarValues::*;
private import MrtmInterfaces::*;
private import LevelPorts::*;
private import MrtmSystemContext::*;
private import NodeDevice::*;

package NodeDeviceContext {

    doc /* Device context: the device as ONE box among the people and things it touches. */
    part fridge : Fridge;
    part device : MedicalDevice;
    part mains : MainsSupply;
    part usbHost : UsbHost;
    part staff : Staff;
    connect fridge.air to device.air;
    connect mains.output to device.mains;
    connect device.usb to usbHost.usb;
    connect device.alarmSignals to staff.alarmSignals;
    connect device.screen to staff.screen;
}
