// NodeDevice — node `device` (level 1, device, IEC 62304 class C); satisfies ONLY its own 70 requirements. Generated by tools/pinned_model.py — edit there. RUN-05.
private import ScalarValues::*;
private import ProjectRequirements::*;
private import MrtmInterfaces::*;
private import LevelPorts::*;
private import NodeHardwareItem::*;
private import NodeSoftwareSystem::*;

package NodeDevice {

    doc /* LEVEL 1 — DEVICE (IEC 60601-1 PEMS; ISO 14971 risk management file 08-safety/). Satisfies the stakeholder and device requirements only. */

    part def MedicalDevice {
        doc /* Black box: the medical device (IEC 60601-1 PEMS) as the clinic meets it. */
        port air : ~ThermalPort;
        port mains : ~PowerPort;
        port usb : UsbPort;
        port alarmSignals : AlarmHmiPort;
        port screen : ScreenPort;
    }
    part def DeviceWhiteBox :> MedicalDevice {
        doc /* White box: ONE hardware item and ONE software system, pinned by IEC 62304 (the software system runs on the hardware item). Wires: package NodeDeviceWhiteBox. */
        part hardwareItem : HardwareItem;
        part softwareSystem : SoftwareSystem;
    }
    part device : MedicalDevice;

    satisfy 'MRTM-ENV-001' by device;
    satisfy 'MRTM-ENV-002' by device;
    satisfy 'MRTM-ENV-003' by device;
    satisfy 'MRTM-ENV-004' by device;
    satisfy 'MRTM-IFC-001' by device;
    satisfy 'MRTM-IFC-002' by device;
    satisfy 'MRTM-IFC-003' by device;
    satisfy 'MRTM-IFC-004' by device;
    satisfy 'MRTM-MNT-001' by device;
    satisfy 'MRTM-MNT-002' by device;
    satisfy 'MRTM-MNT-003' by device;
    satisfy 'MRTM-PRF-001' by device;
    satisfy 'MRTM-PRF-002' by device;
    satisfy 'MRTM-PRF-003' by device;
    satisfy 'MRTM-PRF-004' by device;
    satisfy 'MRTM-SAF-001' by device;
    satisfy 'MRTM-SAF-002' by device;
    satisfy 'MRTM-SAF-003' by device;
    satisfy 'MRTM-SAF-004' by device;
    satisfy 'MRTM-SAF-005' by device;
    satisfy 'MRTM-SAF-006' by device;
    satisfy 'MRTM-SAF-007' by device;
    satisfy 'MRTM-SAF-008' by device;
    satisfy 'MRTM-SAF-009' by device;
    satisfy 'MRTM-SAF-010' by device;
    satisfy 'MRTM-SAF-011' by device;
    satisfy 'MRTM-SAF-012' by device;
    satisfy 'MRTM-SAF-013' by device;
    satisfy 'MRTM-SAF-014' by device;
    satisfy 'MRTM-SAF-015' by device;
    satisfy 'MRTM-SAF-016' by device;
    satisfy 'MRTM-SAF-017' by device;
    satisfy 'MRTM-SAF-018' by device;
    satisfy 'MRTM-SAF-019' by device;
    satisfy 'MRTM-SAF-020' by device;
    satisfy 'MRTM-SAF-021' by device;
    satisfy 'MRTM-SAF-022' by device;
    satisfy 'MRTM-SAF-023' by device;
    satisfy 'MRTM-STK-001' by device;
    satisfy 'MRTM-STK-002' by device;
    satisfy 'MRTM-STK-003' by device;
    satisfy 'MRTM-STK-004' by device;
    satisfy 'MRTM-STK-005' by device;
    satisfy 'MRTM-STK-006' by device;
    satisfy 'MRTM-STK-007' by device;
    satisfy 'MRTM-STK-008' by device;
    satisfy 'MRTM-SYS-001' by device;
    satisfy 'MRTM-SYS-002' by device;
    satisfy 'MRTM-SYS-003' by device;
    satisfy 'MRTM-SYS-004' by device;
    satisfy 'MRTM-SYS-005' by device;
    satisfy 'MRTM-SYS-006' by device;
    satisfy 'MRTM-SYS-007' by device;
    satisfy 'MRTM-SYS-008' by device;
    satisfy 'MRTM-SYS-009' by device;
    satisfy 'MRTM-SYS-010' by device;
    satisfy 'MRTM-SYS-011' by device;
    satisfy 'MRTM-SYS-012' by device;
    satisfy 'MRTM-SYS-013' by device;
    satisfy 'MRTM-SYS-014' by device;
    satisfy 'MRTM-SYS-015' by device;
    satisfy 'MRTM-SYS-016' by device;
    satisfy 'MRTM-SYS-017' by device;
    satisfy 'MRTM-SYS-018' by device;
    satisfy 'MRTM-SYS-019' by device;
    satisfy 'MRTM-SYS-020' by device;
    satisfy 'MRTM-SYS-021' by device;
    satisfy 'MRTM-SYS-022' by device;
    satisfy 'MRTM-SYS-023' by device;
    satisfy 'MRTM-SYS-024' by device;
}
