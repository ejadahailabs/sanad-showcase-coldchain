// NodeHardwareItem — node `hardware-item` (level 2, hardware-item, IEC 62304 class C); satisfies ONLY its own 13 requirements. Generated by tools/pinned_model.py — edit there. RUN-05.
private import ScalarValues::*;
private import ProjectRequirements::*;
private import MrtmInterfaces::*;
private import LevelPorts::*;
private import MrtmHardware::*;

package NodeHardwareItem {

    doc /* LEVEL 2 — HARDWARE ITEM (class C risk controls in hardware: backup alarm, buzzer, probe). */

    part def HardwareItem {
        doc /* The hardware side as ONE item under the device (IEC 60601-1 cl. 4.8 components, cl. 14.8). Outside ports + the signals the software uses. */
        port air : ~ThermalPort;
        port mains : ~PowerPort;
        port usb : UsbPort;
        port alarmSignals : AlarmHmiPort;
        port screen : ScreenPort;
        port hal : ~HalPort;
    }
    part def HardwareItemWhiteBox :> HardwareItem {
        doc /* The chosen parts (09-hardware/). Wires: package NodeHardwareItemParts. */
        part mcu : MrtmHardware::Esp32S3Module;
        part probe : MrtmHardware::Ds18b20;
        part buzzer : MrtmHardware::PiezoBuzzerStage;
        part redLed : MrtmHardware::IndicatorLed;
        part ackButton : MrtmHardware::TactileButton;
        part oled : MrtmHardware::Oled128x64;
        part rtc : MrtmHardware::TcxoRtc;
        part backupTimer : MrtmHardware::WatchdogAlarmTimer;
        part holdUp : MrtmHardware::Supercap;
        part battery : MrtmHardware::LiIonCell;
        part powerPath : MrtmHardware::ChargerPowerPath;
    }
    part hardwareItem : HardwareItem;

    satisfy 'MRTM-HWI-001' by hardwareItem;
    satisfy 'MRTM-HWI-002' by hardwareItem;
    satisfy 'MRTM-HWI-003' by hardwareItem;
    satisfy 'MRTM-HWI-004' by hardwareItem;
    satisfy 'MRTM-HWI-005' by hardwareItem;
    satisfy 'MRTM-HWI-006' by hardwareItem;
    satisfy 'MRTM-HWI-007' by hardwareItem;
    satisfy 'MRTM-HWI-008' by hardwareItem;
    satisfy 'MRTM-HWI-009' by hardwareItem;
    satisfy 'MRTM-HWI-010' by hardwareItem;
    satisfy 'MRTM-HWI-011' by hardwareItem;
    satisfy 'MRTM-HWI-012' by hardwareItem;
    satisfy 'MRTM-HWI-013' by hardwareItem;
}
