// NodeHardwareItemParts — parts of the hardware item (view package, no satisfy). Generated by tools/pinned_model.py — edit there. RUN-05.
private import ScalarValues::*;
private import MrtmInterfaces::*;
private import LevelPorts::*;
private import MrtmHardware::*;

package NodeHardwareItemParts {

    doc /* Inside the hardware item: the chosen parts and their wires. */
    part mcu : Esp32S3Module;
    part probe : Ds18b20;
    part buzzer : PiezoBuzzerStage;
    part redLed : IndicatorLed;
    part ackButton : TactileButton;
    part oled : Oled128x64;
    part rtc : TcxoRtc;
    part backupTimer : WatchdogAlarmTimer;
    part holdUp : Supercap;
    part battery : LiIonCell;
    part powerPath : ChargerPowerPath;
    connect mcu.oneWire to probe.dq;
    connect mcu.buzzerPin to buzzer.drive;
    connect mcu.redPin to redLed.drive;
    connect ackButton.contact to mcu.ackPin;
    connect mcu.i2c to oled.i2c;
    connect mcu.i2c to rtc.i2c;
    connect mcu.wdtKickPin to backupTimer.kick;
    connect backupTimer.alarmOut to buzzer.backupDrive;
    connect holdUp.terminal to backupTimer.holdUp;
    connect battery.terminal to powerPath.batteryIn;
    connect powerPath.output to mcu.supply;
    connect powerPath.output to holdUp.charge;
}
