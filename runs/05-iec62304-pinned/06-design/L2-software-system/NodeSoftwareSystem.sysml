// NodeSoftwareSystem — node `software-system` (level 2, software-system, IEC 62304 class C); satisfies ONLY its own 19 requirements. Generated by tools/pinned_model.py — edit there. RUN-05.
private import ScalarValues::*;
private import ProjectRequirements::*;
private import MrtmInterfaces::*;
private import LevelPorts::*;
private import MrtmSoftware::*;
private import NodeSensorItem::*;
private import NodeExcursionItem::*;
private import NodeAlarmItem::*;
private import NodeDisplayItem::*;
private import NodeLogItem::*;
private import NodeUsbItem::*;
private import NodePowerItem::*;
private import NodeSupervisorItem::*;

package NodeSoftwareSystem {

    doc /* LEVEL 2 — SOFTWARE SYSTEM (IEC 62304 §5.2 SRS, §5.3 architecture). Satisfies the SRS only. */

    part def SoftwareSystem {
        doc /* IEC 62304 software system, class C: the firmware on the hardware item's processor. Its ports are the signals it drives and reads. */
        attribute safetyClass : MrtmSoftware::SafetyClass = MrtmSoftware::SafetyClass::C;
        port hal : HalPort;
    }
    part def SoftwareSystemWhiteBox :> SoftwareSystem {
        doc /* IEC 62304 §5.3.1: the eight software items. Wires: packages NodeSoftwareSystemArchitecture and NodeSoftwareSystemHardwareInterface. */
        part sensorItem : SensorSwItem;
        part excursionItem : ExcursionSwItem;
        part alarmItem : AlarmSwItem;
        part displayItem : DisplaySwItem;
        part logItem : LogSwItem;
        part usbItem : UsbSwItem;
        part powerItem : PowerSwItem;
        part supervisorItem : SupervisorSwItem;
    }
    part softwareSystem : SoftwareSystem;

    satisfy 'MRTM-SRS-001' by softwareSystem;
    satisfy 'MRTM-SRS-002' by softwareSystem;
    satisfy 'MRTM-SRS-003' by softwareSystem;
    satisfy 'MRTM-SRS-004' by softwareSystem;
    satisfy 'MRTM-SRS-005' by softwareSystem;
    satisfy 'MRTM-SRS-006' by softwareSystem;
    satisfy 'MRTM-SRS-007' by softwareSystem;
    satisfy 'MRTM-SRS-008' by softwareSystem;
    satisfy 'MRTM-SRS-009' by softwareSystem;
    satisfy 'MRTM-SRS-010' by softwareSystem;
    satisfy 'MRTM-SRS-011' by softwareSystem;
    satisfy 'MRTM-SRS-012' by softwareSystem;
    satisfy 'MRTM-SRS-013' by softwareSystem;
    satisfy 'MRTM-SRS-014' by softwareSystem;
    satisfy 'MRTM-SRS-015' by softwareSystem;
    satisfy 'MRTM-SRS-016' by softwareSystem;
    satisfy 'MRTM-SRS-017' by softwareSystem;
    satisfy 'MRTM-SRS-018' by softwareSystem;
    satisfy 'MRTM-SRS-019' by softwareSystem;
}
