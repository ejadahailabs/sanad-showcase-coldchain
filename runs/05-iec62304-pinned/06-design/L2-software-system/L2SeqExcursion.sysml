// L2SeqExcursion — item-level excursion sequence (view package, no satisfy). Generated by tools/pinned_model.py — edit there. RUN-05.
private import ScalarValues::*;
private import MrtmInterfaces::*;
private import LevelPorts::*;
private import NodeHardwareItem::*;
private import NodeSensorItem::*;
private import NodeExcursionItem::*;
private import NodeAlarmItem::*;
private import NodeDisplayItem::*;
private import NodeLogItem::*;
private import NodeUsbItem::*;
private import NodePowerItem::*;
private import NodeSupervisorItem::*;

package L2SeqExcursion {

    doc /* Excursion scenario at item level: first out-of-band sample -> low-priority light within 5 s -> confirmation after 31 samples (60 s) -> buzzer, warning, record. */
    part hardwareItem : HardwareItem;
    part sensorItem : SensorSwItem;
    part excursionItem : ExcursionSwItem;
    part alarmItem : AlarmSwItem;
    part displayItem : DisplaySwItem;
    part logItem : LogSwItem;
    message sample of TemperatureSample from hardwareItem to sensorItem;
    message validSample of TemperatureSample from sensorItem to excursionItem;
    message early of ExcursionState from excursionItem to alarmItem;
    message redFlash of AlarmCommand from alarmItem to hardwareItem;
    message confirmed of ExcursionState from excursionItem to alarmItem;
    message buzzerOn of AlarmCommand from alarmItem to hardwareItem;
    message warning of ExcursionState from alarmItem to displayItem;
    message startRecord of LogRecord from alarmItem to logItem;
    succession first sample then validSample;
    succession first validSample then early;
    succession first early then redFlash;
    succession first redFlash then confirmed;
    succession first confirmed then buzzerOn;
    succession first buzzerOn then warning;
    succession first warning then startRecord;
}
