// NodeSoftwareSystemArchitecture — items and their flows (view package, no satisfy). Generated by tools/pinned_model.py — edit there. RUN-05.
private import ScalarValues::*;
private import MrtmInterfaces::*;
private import LevelPorts::*;
private import MrtmSoftware::*;
private import NodeSensorItem::*;
private import NodeExcursionItem::*;
private import NodeAlarmItem::*;
private import NodeDisplayItem::*;
private import NodeLogItem::*;
private import NodeUsbItem::*;
private import NodePowerItem::*;
private import NodeSupervisorItem::*;

package NodeSoftwareSystemArchitecture {

    doc /* Software architecture (IEC 62304 §5.3.1–5.3.2): the eight items and the flows between them. Class B item: usbItem (segregated, ADR-0034). */
    part sensorItem : SensorSwItem;
    part excursionItem : ExcursionSwItem;
    part alarmItem : AlarmSwItem;
    part displayItem : DisplaySwItem;
    part logItem : LogSwItem;
    part usbItem : UsbSwItem;
    part powerItem : PowerSwItem;
    part supervisorItem : SupervisorSwItem;
    connect sensorItem.samples to excursionItem.samples;
    connect sensorItem.samples to displayItem.samples;
    connect excursionItem.excursion to alarmItem.excursion;
    connect alarmItem.alarmState to displayItem.alarmState;
    connect alarmItem.records to logItem.records;
    connect powerItem.records to logItem.records;
    connect supervisorItem.records to logItem.records;
    connect powerItem.events to alarmItem.powerEvents;
    connect alarmItem.heartbeat to supervisorItem.heartbeat;
    connect supervisorItem.band to excursionItem.band;
    connect logItem.history to usbItem.history;
}
