// NodeSoftwareSystemHardwareInterface — items and the hardware item (view package, no satisfy). Generated by tools/pinned_model.py — edit there. RUN-05.
private import ScalarValues::*;
private import MrtmInterfaces::*;
private import LevelPorts::*;
private import MrtmSoftware::*;
private import NodeHardwareItem::*;
private import NodeSensorItem::*;
private import NodeExcursionItem::*;
private import NodeAlarmItem::*;
private import NodeDisplayItem::*;
private import NodeLogItem::*;
private import NodeUsbItem::*;
private import NodePowerItem::*;
private import NodeSupervisorItem::*;

package NodeSoftwareSystemHardwareInterface {

    doc /* Software to hardware (IEC 62304 §5.3.3/§5.3.4 hardware the software needs): which item drives or reads which hardware signal. */
    part sensorItem : SensorSwItem;
    part excursionItem : ExcursionSwItem;
    part alarmItem : AlarmSwItem;
    part displayItem : DisplaySwItem;
    part logItem : LogSwItem;
    part usbItem : UsbSwItem;
    part powerItem : PowerSwItem;
    part supervisorItem : SupervisorSwItem;
    part hardwareItem { port probeBus : ~OneWirePort; port buzzerDrive : ~GpioOutPort; port lightDrive : ~GpioOutPort; port button : ~GpioInPort; port displayBus : ~I2cPort; port clockBus : ~I2cPort; port usbData : ~UsbPort; port mainsSense : ~GpioInPort; port batterySense : PowerPort; port kick : ~GpioOutPort; }  // the hardware item, shown by the signals inside its hal port
    connect sensorItem.bus to hardwareItem.probeBus;
    connect alarmItem.buzzerDrive to hardwareItem.buzzerDrive;
    connect alarmItem.lightDrive to hardwareItem.lightDrive;
    connect hardwareItem.button to alarmItem.button;
    connect displayItem.i2c to hardwareItem.displayBus;
    connect logItem.clock to hardwareItem.clockBus;
    connect usbItem.usb to hardwareItem.usbData;
    connect hardwareItem.mainsSense to powerItem.mainsSense;
    connect hardwareItem.batterySense to powerItem.batterySense;
    connect supervisorItem.pulses to hardwareItem.kick;
}
