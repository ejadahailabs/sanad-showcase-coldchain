package Power_whitebox_interconnectionView {

    comment /* A view file. It imports the packages it draws, exposes elements and names a
       rendering; it declares nothing of the model. Delete it and every package file is
       byte-identical and the model reads unchanged. */

    private import NodePowerWhiteBox::*;
    private import SanadRenderings::*;

    view 'power_whitebox_interconnection' : StandardViewDefinitions::InterconnectionView {
        expose NodePowerWhiteBox::**;
        render asInterconnectionView;
    }
}

package 'Layout_Sanad' {

    comment /* Layout only. Written and read by this workbench.
       Every entry annotates an element by qualified name; no model element is modified.
       Delete this package and the model is unchanged. */

    private import ScalarValues::*;

    metadata def 'Layout' {
        attribute 'viewName' : String;
        attribute 'x' : Real;
        attribute 'y' : Real;
        attribute 'w' : Real;
        attribute 'h' : Real;
    }

    metadata def 'EdgeLayout' {
        attribute 'viewName' : String;
        attribute 'edge' : String;
        attribute 'bends' : String;
    }

    metadata def 'PlainBoxes' {
        attribute 'viewName' : String;
    }

    metadata 'l1' : 'Layout' about 'NodePowerWhiteBox'::'alarm' {
        'viewName' = "power_whitebox_interconnection";
        'x' = 980;
        'y' = 40;
    }

    metadata 'l2' : 'Layout' about 'NodePowerWhiteBox'::'battery' {
        'viewName' = "power_whitebox_interconnection";
        'x' = 340;
        'y' = 300;
    }

    metadata 'l3' : 'Layout' about 'NodePowerWhiteBox'::'logging' {
        'viewName' = "power_whitebox_interconnection";
        'x' = 980;
        'y' = 400;
    }

    metadata 'l4' : 'Layout' about 'NodePowerWhiteBox'::'mainsSupply' {
        'viewName' = "power_whitebox_interconnection";
        'x' = 20;
        'y' = 40;
    }

    metadata 'l5' : 'Layout' about 'NodePowerWhiteBox'::'powerItem' {
        'viewName' = "power_whitebox_interconnection";
        'x' = 660;
        'y' = 300;
    }

    metadata 'l6' : 'Layout' about 'NodePowerWhiteBox'::'powerPath' {
        'viewName' = "power_whitebox_interconnection";
        'x' = 340;
        'y' = 40;
    }

    metadata 'l7' : 'Layout' about 'NodePowerWhiteBox'::'supervision' {
        'viewName' = "power_whitebox_interconnection";
        'x' = 980;
        'y' = 220;
    }

    metadata 'p1' : 'PlainBoxes' {
        'viewName' = "power_whitebox_interconnection";
    }
}
