package Alarm_blackbox_interfacesView {

    comment /* A view file. It imports the packages it draws, exposes elements and names a
       rendering; it declares nothing of the model. Delete it and every package file is
       byte-identical and the model reads unchanged. */

    private import NodeAlarmContext::*;
    private import SanadRenderings::*;

    view 'alarm_blackbox_interfaces' : StandardViewDefinitions::InterconnectionView {
        expose NodeAlarmContext::**;
        render asInterconnectionView;
    }
}

package 'Layout_Sanad' {

    comment /* Layout only. Written and read by this workbench.
       Every entry annotates an element by qualified name; no model element is modified.
       Delete this package and the model is unchanged. */

    private import ScalarValues::*;

    metadata def 'Layout' {
        attribute 'viewName' : String;
        attribute 'x' : Real;
        attribute 'y' : Real;
        attribute 'w' : Real;
        attribute 'h' : Real;
    }

    metadata def 'EdgeLayout' {
        attribute 'viewName' : String;
        attribute 'edge' : String;
        attribute 'bends' : String;
    }

    metadata 'l1' : 'Layout' about 'NodeAlarmContext'::'alarm' {
        'viewName' = "alarm_blackbox_interfaces";
        'x' = 440;
        'y' = 200;
    }

    metadata 'l2' : 'Layout' about 'NodeAlarmContext'::'display' {
        'viewName' = "alarm_blackbox_interfaces";
        'x' = 720;
        'y' = 20;
    }

    metadata 'l3' : 'Layout' about 'NodeAlarmContext'::'logging' {
        'viewName' = "alarm_blackbox_interfaces";
        'x' = 860;
        'y' = 200;
    }

    metadata 'l4' : 'Layout' about 'NodeAlarmContext'::'power' {
        'viewName' = "alarm_blackbox_interfaces";
        'x' = 40;
        'y' = 250;
    }

    metadata 'l5' : 'Layout' about 'NodeAlarmContext'::'sensing' {
        'viewName' = "alarm_blackbox_interfaces";
        'x' = 40;
        'y' = 40;
    }

    metadata 'l6' : 'Layout' about 'NodeAlarmContext'::'staff' {
        'viewName' = "alarm_blackbox_interfaces";
        'x' = 860;
        'y' = 360;
    }

    metadata 'l7' : 'Layout' about 'NodeAlarmContext'::'supervision' {
        'viewName' = "alarm_blackbox_interfaces";
        'x' = 440;
        'y' = 520;
    }
}
