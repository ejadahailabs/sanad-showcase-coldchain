// NodeDisplayItem — node `display-item` (software-item, IEC 62304 class C) of .ejadah/rew/framework.yaml.
// Covers ONLY this node's requirements (2). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeDisplayItem {

    doc /* LEAF `display-item` (software-item). */

    part def DisplaySwItem :> MrtmSoftware::DisplayItem {
        doc /* Software item, class C (two display-only risk controls). Unit: displayMgr. */
        port samples : ~SampleFlow;
        port alarmState : ~AlarmStateFlow;
        port i2c : I2cPort;
    }
    part displaySwItem : DisplaySwItem;

    satisfy 'MRTM-DSI-001' by displaySwItem.displayMgr;
    satisfy 'MRTM-DSI-002' by displaySwItem.displayMgr;
}
