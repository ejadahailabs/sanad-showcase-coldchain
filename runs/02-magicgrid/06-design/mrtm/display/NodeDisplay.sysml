// NodeDisplay — node `display` (subsystem, IEC 62304 class C) of .ejadah/rew/framework.yaml.
// Covers ONLY this node's requirements (3). Generated by tools/levels_model.py — edit there. MODEL-LEVELS.
private import ScalarValues::*;
private import ProjectRequirements::*;
private import MrtmInterfaces::*;
private import NodePorts::*;
private import MrtmSystemContext::*;
private import NodeOled::*;
private import NodeDisplayItem::*;

package NodeDisplay {

    doc /* DISPLAY subsystem (class C: carries two risk controls with no other signal, ADR-0034): shows temperature, warnings and messages. */

    part def Display {
        port samples : ~SampleFlow;
        port alarmState : ~AlarmStateFlow;
        port screen : ScreenPort;
    }

    part def DisplayWhiteBox :> Display {
        part displayItem : DisplaySwItem;
        part oled : Oled;
        // its wires: package NodeDisplayWhiteBox (one file beside this one)
    }
    part display : Display;

    satisfy 'MRTM-DSP-001' by display;
    satisfy 'MRTM-DSP-002' by display;
    satisfy 'MRTM-DSP-003' by display;
}
