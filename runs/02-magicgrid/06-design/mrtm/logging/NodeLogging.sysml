// NodeLogging — node `logging` (subsystem, IEC 62304 class C) of .ejadah/rew/framework.yaml.
// Covers ONLY this node's requirements (4). Generated by tools/levels_model.py — edit there. MODEL-LEVELS.
private import ScalarValues::*;
private import ProjectRequirements::*;
private import MrtmInterfaces::*;
private import NodePorts::*;
private import MrtmSystemContext::*;
private import NodeRtc::*;
private import NodeLogItem::*;
private import NodeUsbItem::*;

package NodeLogging {

    doc /* LOGGING-AND-HISTORY subsystem (class C; its USB item is class B with segregation, ADR-0034): keeps 10 000 time-stamped events and gives them read-only over USB. */

    part def Logging {
        port records : ~RecordFlow;
        port usb : UsbPort;
    }

    part def LoggingWhiteBox :> Logging {
        part logItem : LogSwItem;
        part rtc : Rtc;
        part usbItem : UsbSwItem;
        // its wires: package NodeLoggingWhiteBox (one file beside this one)
    }
    part logging : Logging;

    satisfy 'MRTM-LOG-001' by logging;
    satisfy 'MRTM-LOG-002' by logging;
    satisfy 'MRTM-LOG-003' by logging;
    satisfy 'MRTM-LOG-004' by logging;
}
