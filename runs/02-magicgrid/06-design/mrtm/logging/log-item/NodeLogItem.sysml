// NodeLogItem — node `log-item` (software-item, IEC 62304 class C) of .ejadah/rew/framework.yaml.
// Covers ONLY this node's requirements (2). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeLogItem {

    doc /* LEAF `log-item` (software-item). */

    part def LogSwItem :> MrtmSoftware::LogItem {
        doc /* Software item, class C. Units: eventLog, historyRing, rtcClock. */
        port records : ~RecordFlow;
        port clock : I2cPort;
        port history : HistoryFlow;
    }
    part logSwItem : LogSwItem;

    satisfy 'MRTM-LGI-001' by logSwItem.eventLog;
    satisfy 'MRTM-LGI-002' by logSwItem.eventLog;
}
