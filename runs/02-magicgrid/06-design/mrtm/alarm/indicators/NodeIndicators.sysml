// NodeIndicators — node `indicators` (hardware-part, IEC 62304 class C) of .ejadah/rew/framework.yaml.
// Covers ONLY this node's requirements (2). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeIndicators {

    doc /* LEAF `indicators` (hardware-part). */

    part def Indicators :> MrtmHardware::Component {
        doc /* Chosen parts: red and green indicator lamps and the acknowledge button, on one front panel. */
        port redDrive : ~GpioOutPort;
        port contact : ~GpioInPort;
        part redLed : MrtmHardware::IndicatorLed;
        part greenLed : MrtmHardware::IndicatorLed;
        part ackButton : MrtmHardware::TactileButton;
    }
    part indicators : Indicators;

    satisfy 'MRTM-IND-001' by indicators;
    satisfy 'MRTM-IND-002' by indicators;
}
