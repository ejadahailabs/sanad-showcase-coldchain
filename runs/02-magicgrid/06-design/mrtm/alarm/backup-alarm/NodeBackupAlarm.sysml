// NodeBackupAlarm — node `backup-alarm` (assembly, IEC 62304 class C) of .ejadah/rew/framework.yaml.
// Covers ONLY this node's requirements (2). Generated by tools/levels_model.py — edit there. MODEL-LEVELS.
private import ScalarValues::*;
private import ProjectRequirements::*;
private import MrtmInterfaces::*;
private import NodePorts::*;
private import NodeBackupTimer::*;
private import NodeBackupDriver::*;
private import NodeHoldUp::*;

package NodeBackupAlarm {

    doc /* BACKUP ALARM assembly (class C risk control for HAZ-003, HAZ-005; ADR-0013): the step repeats here — its own black box and white box — because it needs no processor and must be argued on its own. */

    part def BackupAlarmAssembly {
        port kick : ~GpioOutPort;
        port supply : ~PowerPort;
        port drive : GpioOutPort;
    }

    part def BackupAlarmWhiteBox :> BackupAlarmAssembly {
        part timer : BackupTimer;
        part driver : BackupDriver;
        part holdUp : HoldUp;
        // its wires: package NodeBackupAlarmWhiteBox (one file beside this one)
    }
    part backupAlarm : BackupAlarmAssembly;

    satisfy 'MRTM-BKA-001' by backupAlarm;
    satisfy 'MRTM-BKA-002' by backupAlarm;
}
