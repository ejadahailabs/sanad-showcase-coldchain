// NodeBackupDriver — node `backup-driver` (hardware-part, IEC 62304 class C) of .ejadah/rew/framework.yaml.
// Covers ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeBackupDriver {

    doc /* LEAF `backup-driver` (hardware-part). */

    part def BackupDriver :> MrtmHardware::Component {
        doc /* Chosen part: transistor stage from the timer output to the buzzer's backup input. Drawn inside the buzzer stage until MODEL-LEVELS (A-44, EE-REVIEW). */
        port input : ~GpioOutPort;
        port output : GpioOutPort;
        port supply : ~PowerPort;
    }
    part backupDriver : BackupDriver;

    satisfy 'MRTM-BKD-001' by backupDriver;
}
