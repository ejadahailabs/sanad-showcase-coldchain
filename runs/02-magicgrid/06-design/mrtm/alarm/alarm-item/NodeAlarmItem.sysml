// NodeAlarmItem — node `alarm-item` (software-item, IEC 62304 class C) of .ejadah/rew/framework.yaml.
// Covers ONLY this node's requirements (4). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeAlarmItem {

    doc /* LEAF `alarm-item` (software-item). */

    part def AlarmSwItem :> MrtmSoftware::AlarmItem {
        doc /* Software item, class C. Unit: alarmMgr (the alarm state machine). */
        port excursion : ~ExcursionFlow;
        port alarmState : AlarmStateFlow;
        port records : RecordFlow;
        port powerEvents : ~PowerEventFlow;
        port heartbeat : HeartbeatFlow;
        port buzzerDrive : GpioOutPort;
        port lightDrive : GpioOutPort;
        port button : GpioInPort;
    }
    part alarmSwItem : AlarmSwItem;

    satisfy 'MRTM-ALI-001' by alarmSwItem.alarmMgr;
    satisfy 'MRTM-ALI-002' by alarmSwItem.alarmMgr;
    satisfy 'MRTM-ALI-003' by alarmSwItem.alarmMgr;
    satisfy 'MRTM-ALI-004' by alarmSwItem.alarmMgr;
}
