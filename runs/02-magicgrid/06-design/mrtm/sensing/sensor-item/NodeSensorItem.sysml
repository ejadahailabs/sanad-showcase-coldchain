// NodeSensorItem — node `sensor-item` (software-item, IEC 62304 class C) of .ejadah/rew/framework.yaml.
// Covers ONLY this node's requirements (2). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeSensorItem {

    doc /* LEAF `sensor-item` (software-item). */

    part def SensorSwItem :> MrtmSoftware::SensorItem {
        doc /* Software item (IEC 62304 §5.3.1), class C. Unit: sensorSampler. */
        port bus : OneWirePort;
        port samples : SampleFlow;
    }
    part sensorSwItem : SensorSwItem;

    satisfy 'MRTM-SNI-001' by sensorSwItem.sensorSampler;
    satisfy 'MRTM-SNI-002' by sensorSwItem.sensorSampler;
}
