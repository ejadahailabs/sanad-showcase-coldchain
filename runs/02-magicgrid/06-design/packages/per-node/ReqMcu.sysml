package ReqMcu {
    comment /* GENERATED from the Markdown requirement corpus at 74d335246edb19b4.
       Read-only: edit the Markdown requirement, not this file. Sanad regenerates it on
       every corpus change and the same corpus always gives byte-identical text. */

    requirement <'MRTM-MCU-001'> MRTM_MCU_001 {
        doc /* The microcontroller shall reset within 1 s of its hardware watchdog expiry. */
    }
}
