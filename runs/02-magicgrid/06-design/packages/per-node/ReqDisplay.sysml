package ReqDisplay {
    comment /* GENERATED from the Markdown requirement corpus at 25e6f2bbabec4290.
       Read-only: edit the Markdown requirement, not this file. Sanad regenerates it on
       every corpus change and the same corpus always gives byte-identical text. */

    requirement <'MRTM-DSP-001'> MRTM_DSP_001 {
        doc /* The display subsystem shall show the excursion warning within 1 s of excursion confirmation until the excursion ends. */
    }

    requirement <'MRTM-DSP-002'> MRTM_DSP_002 {
        doc /* The display subsystem shall show the current temperature at 0.1 °C resolution in digits of 5 mm or more, refreshed at a period of 10 s. */
    }

    requirement <'MRTM-DSP-003'> MRTM_DSP_003 {
        doc /* The display subsystem shall show the probe fault, calibration due, band limits and log capacity messages within 1 s of their cause. */
    }
}
