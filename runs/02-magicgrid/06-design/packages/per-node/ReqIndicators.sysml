package ReqIndicators {
    comment /* GENERATED from the Markdown requirement corpus at f23a06a30d5a27d8.
       Read-only: edit the Markdown requirement, not this file. Sanad regenerates it on
       every corpus change and the same corpus always gives byte-identical text. */

    requirement <'MRTM-IND-001'> MRTM_IND_001 {
        doc /* The red indicator shall follow its drive input within 10 ms. */
    }

    requirement <'MRTM-IND-002'> MRTM_IND_002 {
        doc /* While a clinic staff member presses the acknowledge button, the button shall close the contact that signals an **Acknowledgement**. */
    }
}
