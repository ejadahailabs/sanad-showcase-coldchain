package ReqRtc {
    comment /* GENERATED from the Markdown requirement corpus at 316c5174e3b21fc7.
       Read-only: edit the Markdown requirement, not this file. Sanad regenerates it on
       every corpus change and the same corpus always gives byte-identical text. */

    requirement <'MRTM-RTC-001'> MRTM_RTC_001 {
        doc /* The real-time clock shall keep time with a drift of 2 s per day or less from 10 °C to 35 °C. */
    }
}
