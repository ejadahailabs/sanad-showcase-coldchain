package ReqHoldUp {
    comment /* GENERATED from the Markdown requirement corpus at 18f63a8bdac792ef.
       Read-only: edit the Markdown requirement, not this file. Sanad regenerates it on
       every corpus change and the same corpus always gives byte-identical text. */

    requirement <'MRTM-BKH-001'> MRTM_BKH_001 {
        doc /* The hold-up store shall supply the backup timer and the backup driver for 60 s or more after all power is lost. */
    }
}
