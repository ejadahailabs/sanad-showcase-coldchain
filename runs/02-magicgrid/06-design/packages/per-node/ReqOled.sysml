package ReqOled {
    comment /* GENERATED from the Markdown requirement corpus at d62452d875bc32ac.
       Read-only: edit the Markdown requirement, not this file. Sanad regenerates it on
       every corpus change and the same corpus always gives byte-identical text. */

    requirement <'MRTM-OLD-001'> MRTM_OLD_001 {
        doc /* The display panel shall draw the temperature digits at a character height of 5 mm or more. */
    }
}
