package ReqPowerPath {
    comment /* GENERATED from the Markdown requirement corpus at f706ead5e79bb4df.
       Read-only: edit the Markdown requirement, not this file. Sanad regenerates it on
       every corpus change and the same corpus always gives byte-identical text. */

    requirement <'MRTM-PPT-001'> MRTM_PPT_001 {
        doc /* The power path shall switch the load from mains to battery within 100 ms. */
    }
}
