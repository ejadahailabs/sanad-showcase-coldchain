package ReqBackupDriver {
    comment /* GENERATED from the Markdown requirement corpus at 898acccf9c34750f.
       Read-only: edit the Markdown requirement, not this file. Sanad regenerates it on
       every corpus change and the same corpus always gives byte-identical text. */

    requirement <'MRTM-BKD-001'> MRTM_BKD_001 {
        doc /* The backup driver shall drive the buzzer backup input within 100 ms of the timeout output. */
    }
}
