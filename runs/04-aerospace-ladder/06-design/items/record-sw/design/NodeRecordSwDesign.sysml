// NodeRecordSwDesign — RUN-04 aerospace ladder. Generated by tools/aero_model.py — edit there.
private import ScalarValues::*;
private import ProjectRequirements::*;
private import RecordSwArchitecture::*;

package NodeRecordSwDesign {

    doc /* SOFTWARE DESIGN of `record-sw` (DO-178C §5.2): its architecture and its low-level requirements. Covers its own LLR only, each by the component whose code implements it. */

    part recordSwDesign : RecordSwDesign;

    satisfy 'MRTM-LLR-035' by recordSwDesign.eventLog;
    satisfy 'MRTM-LLR-036' by recordSwDesign.eventLog;
    satisfy 'MRTM-LLR-037' by recordSwDesign.historyRing;
    satisfy 'MRTM-LLR-038' by recordSwDesign.historyRing;
    satisfy 'MRTM-LLR-039' by recordSwDesign.historyRing;
    satisfy 'MRTM-LLR-040' by recordSwDesign.rtcClock;
    satisfy 'MRTM-LLR-041' by recordSwDesign.rtcClock;
    satisfy 'MRTM-LLR-042' by recordSwDesign.rtcClock;
}
