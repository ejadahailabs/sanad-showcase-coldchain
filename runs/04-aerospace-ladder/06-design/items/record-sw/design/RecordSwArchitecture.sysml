// RecordSwArchitecture — RUN-04 aerospace ladder. Generated by tools/aero_model.py — edit there.
private import ScalarValues::*;
private import SoftwareProfile::*;
private import MrtmInterfaces::*;
private import MrtmSoftware::*;

package RecordSwArchitecture {

    doc /* Software architecture of `record-sw` (DO-178C §5.2.1) with Sanad's software profile (#Component, #Thread from MrtmSoftware). No satisfy here. */

    part def RecordSwDesign {
        part eventLog : EventLog;
        part historyRing : HistoryRingStore;
        part rtcClock : RtcClock;
        part logTask : LogTask;
        allocate eventLog to logTask;
        allocate historyRing to logTask;
        allocate rtcClock to logTask;
    }
}
