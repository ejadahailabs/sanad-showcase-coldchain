// NodeRecordSw — RUN-04 aerospace ladder. Generated by tools/aero_model.py — edit there.
private import ScalarValues::*;
private import ProjectRequirements::*;
private import MrtmInterfaces::*;
private import AeroPorts::*;

package NodeRecordSw {

    doc /* ITEM `record-sw` (ARP4754A §5.3 item, DAL C). Covers its own high-level requirements (DO-178C §5.1) only. */

    part def RecordSw {
        doc /* Time-stamps every event and keeps two copies in flash. */
        attribute itemDal : DesignAssuranceLevel = DesignAssuranceLevel::C;
        port records : ~RecordFlow;
        port history : HistoryFlow;
    }
    part recordSw : RecordSw;

    satisfy 'MRTM-HLR-030' by recordSw;
    satisfy 'MRTM-HLR-031' by recordSw;
    satisfy 'MRTM-HLR-032' by recordSw;
    satisfy 'MRTM-HLR-033' by recordSw;
    satisfy 'MRTM-HLR-034' by recordSw;
}
