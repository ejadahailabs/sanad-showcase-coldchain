// NodeDisplayHw — RUN-04 aerospace ladder. Generated by tools/aero_model.py — edit there.
private import ScalarValues::*;
private import ProjectRequirements::*;
private import MrtmInterfaces::*;
private import AeroPorts::*;

package NodeDisplayHw {

    doc /* ITEM `display-hw` (ARP4754A §5.3 item, DAL B). Covers its own hardware item requirements only. */

    part def DisplayHw {
        doc /* The 0.96 in OLED panel on the I2C bus. */
        attribute itemDal : DesignAssuranceLevel = DesignAssuranceLevel::B;
        port i2c : ~I2cPort;
        port supply : ~PowerPort;
        port screen : ScreenPort;
    }
    part displayHw : DisplayHw;

    satisfy 'MRTM-HWR-014' by displayHw;
}
