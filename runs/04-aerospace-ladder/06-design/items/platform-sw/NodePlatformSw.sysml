// NodePlatformSw — RUN-04 aerospace ladder. Generated by tools/aero_model.py — edit there.
private import ScalarValues::*;
private import ProjectRequirements::*;
private import MrtmInterfaces::*;
private import AeroPorts::*;

package NodePlatformSw {

    doc /* ITEM `platform-sw` (ARP4754A §5.3 item, DAL A). Covers its own high-level requirements (DO-178C §5.1) only. */

    part def PlatformSw {
        doc /* Power-up order and self-tests, the band check, the watchdog gate, mains and battery events, task priorities. */
        attribute itemDal : DesignAssuranceLevel = DesignAssuranceLevel::A;
        port heartbeat : ~HeartbeatFlow;
        port band : BandFlow;
        port powerEvents : PowerEventFlow;
        port records : RecordFlow;
    }
    part platformSw : PlatformSw;

    satisfy 'MRTM-HLR-016' by platformSw;
    satisfy 'MRTM-HLR-017' by platformSw;
    satisfy 'MRTM-HLR-018' by platformSw;
    satisfy 'MRTM-HLR-019' by platformSw;
    satisfy 'MRTM-HLR-020' by platformSw;
    satisfy 'MRTM-HLR-021' by platformSw;
    satisfy 'MRTM-HLR-022' by platformSw;
    satisfy 'MRTM-HLR-023' by platformSw;
    satisfy 'MRTM-HLR-024' by platformSw;
}
