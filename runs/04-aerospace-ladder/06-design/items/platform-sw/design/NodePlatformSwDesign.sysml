// NodePlatformSwDesign — RUN-04 aerospace ladder. Generated by tools/aero_model.py — edit there.
private import ScalarValues::*;
private import ProjectRequirements::*;
private import PlatformSwArchitecture::*;

package NodePlatformSwDesign {

    doc /* SOFTWARE DESIGN of `platform-sw` (DO-178C §5.2): its architecture and its low-level requirements. Covers its own LLR only, each by the component whose code implements it. */

    part platformSwDesign : PlatformSwDesign;

    satisfy 'MRTM-LLR-017' by platformSwDesign.wdtKicker;
    satisfy 'MRTM-LLR-018' by platformSwDesign.wdtKicker;
    satisfy 'MRTM-LLR-019' by platformSwDesign.diagnostics;
    satisfy 'MRTM-LLR-020' by platformSwDesign.configMgr;
    satisfy 'MRTM-LLR-021' by platformSwDesign.configMgr;
    satisfy 'MRTM-LLR-022' by platformSwDesign;
    satisfy 'MRTM-LLR-023' by platformSwDesign.powerMon;
    satisfy 'MRTM-LLR-024' by platformSwDesign.powerMon;
    satisfy 'MRTM-LLR-025' by platformSwDesign;
    satisfy 'MRTM-LLR-026' by platformSwDesign;
}
