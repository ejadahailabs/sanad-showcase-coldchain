// PlatformSwArchitecture — RUN-04 aerospace ladder. Generated by tools/aero_model.py — edit there.
private import ScalarValues::*;
private import SoftwareProfile::*;
private import MrtmInterfaces::*;
private import MrtmSoftware::*;

package PlatformSwArchitecture {

    doc /* Software architecture of `platform-sw` (DO-178C §5.2.1) with Sanad's software profile (#Component, #Thread from MrtmSoftware). No satisfy here. */

    part def PlatformSwDesign {
        part wdtKicker : WdtKicker;
        part diagnostics : Diagnostics;
        part configMgr : ConfigMgr;
        part powerMon : PowerMon;
        part supervisorTask : SupervisorTask;
        allocate wdtKicker to supervisorTask;
        allocate diagnostics to supervisorTask;
        allocate configMgr to supervisorTask;
        allocate powerMon to supervisorTask;
    }
}
