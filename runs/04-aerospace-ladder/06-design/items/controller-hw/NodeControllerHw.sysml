// NodeControllerHw — RUN-04 aerospace ladder. Generated by tools/aero_model.py — edit there.
private import ScalarValues::*;
private import ProjectRequirements::*;
private import MrtmInterfaces::*;
private import AeroPorts::*;

package NodeControllerHw {

    doc /* ITEM `controller-hw` (ARP4754A §5.3 item, DAL A). Covers its own hardware item requirements only. */

    part def ControllerHw {
        doc /* The processor board: ESP32-S3 class microcontroller, real-time clock, flash. Hosts all five software items. */
        attribute itemDal : DesignAssuranceLevel = DesignAssuranceLevel::A;
        port probeBus : OneWirePort;
        port i2c : I2cPort;
        port buzzerDrive : GpioOutPort;
        port redLed : GpioOutPort;
        port wdtPulse : GpioOutPort;
        port ack : GpioInPort;
        port buzzerSense : GpioInPort;
        port mainsSense : GpioInPort;
        port usb : UsbPort;
        port supply : ~PowerPort;
    }
    part controllerHw : ControllerHw;

    satisfy 'MRTM-HWR-010' by controllerHw;
    satisfy 'MRTM-HWR-011' by controllerHw;
}
