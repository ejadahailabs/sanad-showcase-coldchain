// NodeExportSwDesign — RUN-04 aerospace ladder. Generated by tools/aero_model.py — edit there.
private import ScalarValues::*;
private import ProjectRequirements::*;
private import ExportSwArchitecture::*;

package NodeExportSwDesign {

    doc /* SOFTWARE DESIGN of `export-sw` (DO-178C §5.2): its architecture and its low-level requirements. Covers its own LLR only, each by the component whose code implements it. */

    part exportSwDesign : ExportSwDesign;

    satisfy 'MRTM-LLR-043' by exportSwDesign.usbExport;
    satisfy 'MRTM-LLR-044' by exportSwDesign.usbExport;
    satisfy 'MRTM-LLR-045' by exportSwDesign.usbExport;
}
