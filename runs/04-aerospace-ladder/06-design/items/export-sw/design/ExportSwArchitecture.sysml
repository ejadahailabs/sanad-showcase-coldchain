// ExportSwArchitecture — RUN-04 aerospace ladder. Generated by tools/aero_model.py — edit there.
private import ScalarValues::*;
private import SoftwareProfile::*;
private import MrtmInterfaces::*;
private import MrtmSoftware::*;

package ExportSwArchitecture {

    doc /* Software architecture of `export-sw` (DO-178C §5.2.1) with Sanad's software profile (#Component, #Thread from MrtmSoftware). No satisfy here. */

    part def ExportSwDesign {
        part usbExport : UsbExport;
        part usbTask : UsbTask;
        allocate usbExport to usbTask;
    }
}
