// NodeExportSw — RUN-04 aerospace ladder. Generated by tools/aero_model.py — edit there.
private import ScalarValues::*;
private import ProjectRequirements::*;
private import MrtmInterfaces::*;
private import AeroPorts::*;

package NodeExportSw {

    doc /* ITEM `export-sw` (ARP4754A §5.3 item, DAL D). Covers its own high-level requirements (DO-178C §5.1) only. */

    part def ExportSw {
        doc /* Shows the history to a USB host as a read-only volume. */
        attribute itemDal : DesignAssuranceLevel = DesignAssuranceLevel::D;
        port history : ~HistoryFlow;
    }
    part exportSw : ExportSw;

    satisfy 'MRTM-HLR-035' by exportSw;
    satisfy 'MRTM-HLR-036' by exportSw;
    satisfy 'MRTM-HLR-037' by exportSw;
}
