// NodeAlarmHw — RUN-04 aerospace ladder. Generated by tools/aero_model.py — edit there.
private import ScalarValues::*;
private import ProjectRequirements::*;
private import MrtmInterfaces::*;
private import AeroPorts::*;

package NodeAlarmHw {

    doc /* ITEM `alarm-hw` (ARP4754A §5.3 item, DAL A). Covers its own hardware item requirements only. */

    part def AlarmHw {
        doc /* Buzzer, red and green lights, acknowledge button and the backup alarm (external watchdog timer, driver, hold-up store). */
        attribute itemDal : DesignAssuranceLevel = DesignAssuranceLevel::A;
        port buzzerDrive : ~GpioOutPort;
        port redLed : ~GpioOutPort;
        port wdtPulse : ~GpioOutPort;
        port ack : ~GpioInPort;
        port buzzerSense : ~GpioInPort;
        port supply : ~PowerPort;
        port alarmSignals : AlarmHmiPort;
    }
    part alarmHw : AlarmHw;

    satisfy 'MRTM-HWR-004' by alarmHw;
    satisfy 'MRTM-HWR-005' by alarmHw;
    satisfy 'MRTM-HWR-006' by alarmHw;
    satisfy 'MRTM-HWR-007' by alarmHw;
    satisfy 'MRTM-HWR-008' by alarmHw;
    satisfy 'MRTM-HWR-009' by alarmHw;
}
