// DisplaySwArchitecture — RUN-04 aerospace ladder. Generated by tools/aero_model.py — edit there.
private import ScalarValues::*;
private import SoftwareProfile::*;
private import MrtmInterfaces::*;
private import MrtmSoftware::*;

package DisplaySwArchitecture {

    doc /* Software architecture of `display-sw` (DO-178C §5.2.1) with Sanad's software profile (#Component, #Thread from MrtmSoftware). No satisfy here. */

    part def DisplaySwDesign {
        part displayMgr : DisplayMgr;
        part displayTask : DisplayTask;
        allocate displayMgr to displayTask;
    }
}
