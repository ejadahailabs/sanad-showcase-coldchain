// NodeDisplaySwDesign — RUN-04 aerospace ladder. Generated by tools/aero_model.py — edit there.
private import ScalarValues::*;
private import ProjectRequirements::*;
private import DisplaySwArchitecture::*;

package NodeDisplaySwDesign {

    doc /* SOFTWARE DESIGN of `display-sw` (DO-178C §5.2): its architecture and its low-level requirements. Covers its own LLR only, each by the component whose code implements it. */

    part displaySwDesign : DisplaySwDesign;

    satisfy 'MRTM-LLR-027' by displaySwDesign;
    satisfy 'MRTM-LLR-028' by displaySwDesign.displayMgr;
    satisfy 'MRTM-LLR-029' by displaySwDesign.displayMgr;
    satisfy 'MRTM-LLR-030' by displaySwDesign.displayMgr;
    satisfy 'MRTM-LLR-031' by displaySwDesign.displayMgr;
    satisfy 'MRTM-LLR-032' by displaySwDesign.displayMgr;
    satisfy 'MRTM-LLR-033' by displaySwDesign.displayMgr;
    satisfy 'MRTM-LLR-034' by displaySwDesign.displayMgr;
}
