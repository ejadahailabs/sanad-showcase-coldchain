// NodeDisplaySw — RUN-04 aerospace ladder. Generated by tools/aero_model.py — edit there.
private import ScalarValues::*;
private import ProjectRequirements::*;
private import MrtmInterfaces::*;
private import AeroPorts::*;

package NodeDisplaySw {

    doc /* ITEM `display-sw` (ARP4754A §5.3 item, DAL B). Covers its own high-level requirements (DO-178C §5.1) only. */

    part def DisplaySw {
        doc /* Draws the temperature, the warning and the maintenance messages. */
        attribute itemDal : DesignAssuranceLevel = DesignAssuranceLevel::B;
        port samples : ~SampleFlow;
        port alarmState : ~AlarmStateFlow;
    }
    part displaySw : DisplaySw;

    satisfy 'MRTM-HLR-025' by displaySw;
    satisfy 'MRTM-HLR-026' by displaySw;
    satisfy 'MRTM-HLR-027' by displaySw;
    satisfy 'MRTM-HLR-028' by displaySw;
    satisfy 'MRTM-HLR-029' by displaySw;
}
