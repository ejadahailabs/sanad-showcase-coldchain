// NodePowerHw — RUN-04 aerospace ladder. Generated by tools/aero_model.py — edit there.
private import ScalarValues::*;
private import ProjectRequirements::*;
private import MrtmInterfaces::*;
private import AeroPorts::*;

package NodePowerHw {

    doc /* ITEM `power-hw` (ARP4754A §5.3 item, DAL B). Covers its own hardware item requirements only. */

    part def PowerHw {
        doc /* Mains adapter input, power path and the Li-ion battery. */
        attribute itemDal : DesignAssuranceLevel = DesignAssuranceLevel::B;
        port mains : ~PowerPort;
        port supply : PowerPort;
        port mainsSense : ~GpioInPort;
    }
    part powerHw : PowerHw;

    satisfy 'MRTM-HWR-012' by powerHw;
    satisfy 'MRTM-HWR-013' by powerHw;
}
