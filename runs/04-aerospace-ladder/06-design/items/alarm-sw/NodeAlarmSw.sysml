// NodeAlarmSw — RUN-04 aerospace ladder. Generated by tools/aero_model.py — edit there.
private import ScalarValues::*;
private import ProjectRequirements::*;
private import MrtmInterfaces::*;
private import AeroPorts::*;

package NodeAlarmSw {

    doc /* ITEM `alarm-sw` (ARP4754A §5.3 item, DAL A). Covers its own high-level requirements (DO-178C §5.1) only. */

    part def AlarmSw {
        doc /* Samples the probe, decides early / confirmed / ended excursions and drives the alarm signals. The alarm path. */
        attribute itemDal : DesignAssuranceLevel = DesignAssuranceLevel::A;
        port samples : SampleFlow;
        port alarmState : AlarmStateFlow;
        port records : RecordFlow;
        port heartbeat : HeartbeatFlow;
        port band : ~BandFlow;
        port powerEvents : ~PowerEventFlow;
    }
    part alarmSw : AlarmSw;

    satisfy 'MRTM-HLR-001' by alarmSw;
    satisfy 'MRTM-HLR-002' by alarmSw;
    satisfy 'MRTM-HLR-003' by alarmSw;
    satisfy 'MRTM-HLR-004' by alarmSw;
    satisfy 'MRTM-HLR-005' by alarmSw;
    satisfy 'MRTM-HLR-006' by alarmSw;
    satisfy 'MRTM-HLR-007' by alarmSw;
    satisfy 'MRTM-HLR-008' by alarmSw;
    satisfy 'MRTM-HLR-009' by alarmSw;
    satisfy 'MRTM-HLR-010' by alarmSw;
    satisfy 'MRTM-HLR-011' by alarmSw;
    satisfy 'MRTM-HLR-012' by alarmSw;
    satisfy 'MRTM-HLR-013' by alarmSw;
    satisfy 'MRTM-HLR-014' by alarmSw;
    satisfy 'MRTM-HLR-015' by alarmSw;
    satisfy 'MRTM-HLR-038' by alarmSw;
}
