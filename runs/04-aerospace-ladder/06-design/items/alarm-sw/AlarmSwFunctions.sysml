// AlarmSwFunctions — RUN-04 aerospace ladder. Generated by tools/aero_model.py — edit there.
private import MrtmInterfaces::*;
private import MrtmSwStates::*;

package AlarmSwFunctions {

    doc /* Functional decomposition of the alarm software item (item level): what its HLR ask, in order. No satisfy here. */

    action def AlarmPath {
        action sampleProbe { doc /* HLR-001 */ out item raw : TemperatureSample; }
        action checkSample { doc /* HLR-002, HLR-003 */ in item raw : TemperatureSample; out item valid : TemperatureSample; }
        action countExcursion { doc /* HLR-004…006 */ in item valid : TemperatureSample; out item excursion : ExcursionState; }
        action decideAlarm { doc /* HLR-007…015: the alarm state machine */ in item excursion : ExcursionState; in item press : ButtonPress; out item command : AlarmCommand; }
        action driveSignals { doc /* buzzer, red light */ in item command : AlarmCommand; }
        action beatHeart { doc /* HLR-010 */ }
        flow of TemperatureSample from sampleProbe.raw to checkSample.raw;
        flow of TemperatureSample from checkSample.valid to countExcursion.valid;
        flow of ExcursionState from countExcursion.excursion to decideAlarm.excursion;
        flow of AlarmCommand from decideAlarm.command to driveSignals.command;
        succession first decideAlarm then beatHeart;
    }
}
