// NodeAlarmSwDesign — RUN-04 aerospace ladder. Generated by tools/aero_model.py — edit there.
private import ScalarValues::*;
private import ProjectRequirements::*;
private import AlarmSwArchitecture::*;

package NodeAlarmSwDesign {

    doc /* SOFTWARE DESIGN of `alarm-sw` (DO-178C §5.2): its architecture and its low-level requirements. Covers its own LLR only, each by the component whose code implements it. */

    part alarmSwDesign : AlarmSwDesign;

    satisfy 'MRTM-LLR-001' by alarmSwDesign.sensorSampler;
    satisfy 'MRTM-LLR-002' by alarmSwDesign.sensorSampler;
    satisfy 'MRTM-LLR-003' by alarmSwDesign.sensorSampler;
    satisfy 'MRTM-LLR-004' by alarmSwDesign.sensorSampler;
    satisfy 'MRTM-LLR-005' by alarmSwDesign;
    satisfy 'MRTM-LLR-006' by alarmSwDesign;
    satisfy 'MRTM-LLR-007' by alarmSwDesign.limitEvaluator;
    satisfy 'MRTM-LLR-008' by alarmSwDesign.limitEvaluator;
    satisfy 'MRTM-LLR-009' by alarmSwDesign.limitEvaluator;
    satisfy 'MRTM-LLR-010' by alarmSwDesign.alarmMgr;
    satisfy 'MRTM-LLR-011' by alarmSwDesign.alarmMgr;
    satisfy 'MRTM-LLR-012' by alarmSwDesign.alarmMgr;
    satisfy 'MRTM-LLR-013' by alarmSwDesign.alarmMgr;
    satisfy 'MRTM-LLR-014' by alarmSwDesign.alarmMgr;
    satisfy 'MRTM-LLR-015' by alarmSwDesign.alarmMgr;
    satisfy 'MRTM-LLR-016' by alarmSwDesign.alarmMgr;
}
