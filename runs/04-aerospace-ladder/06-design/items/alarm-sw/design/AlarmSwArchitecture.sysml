// AlarmSwArchitecture — RUN-04 aerospace ladder. Generated by tools/aero_model.py — edit there.
private import ScalarValues::*;
private import SoftwareProfile::*;
private import MrtmInterfaces::*;
private import MrtmSoftware::*;

package AlarmSwArchitecture {

    doc /* Software architecture of `alarm-sw` (DO-178C §5.2.1) with Sanad's software profile (#Component, #Thread from MrtmSoftware). No satisfy here. */

    part def AlarmSwDesign {
        part sensorSampler : SensorSampler;
        part limitEvaluator : LimitEvaluator;
        part alarmMgr : AlarmMgr;
        part sensorTask : SensorTask;
        part alarmTask : AlarmTask;
        connect sensorSampler.samples to limitEvaluator.samples;
        connect limitEvaluator.excursion to alarmMgr.excursion;
        allocate sensorSampler to sensorTask;
        allocate limitEvaluator to sensorTask;
        allocate alarmMgr to alarmTask;
    }
}
