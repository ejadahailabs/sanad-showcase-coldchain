// NodeSensorHw — RUN-04 aerospace ladder. Generated by tools/aero_model.py — edit there.
private import ScalarValues::*;
private import ProjectRequirements::*;
private import MrtmInterfaces::*;
private import AeroPorts::*;

package NodeSensorHw {

    doc /* ITEM `sensor-hw` (ARP4754A §5.3 item, DAL A). Covers its own hardware item requirements only. */

    part def SensorHw {
        doc /* The temperature probe on its 1-Wire bus (DS18B20 class, synthetic). */
        attribute itemDal : DesignAssuranceLevel = DesignAssuranceLevel::A;
        port air : ~ThermalPort;
        port bus : ~OneWirePort;
    }
    part sensorHw : SensorHw;

    satisfy 'MRTM-HWR-001' by sensorHw;
    satisfy 'MRTM-HWR-002' by sensorHw;
    satisfy 'MRTM-HWR-003' by sensorHw;
}
