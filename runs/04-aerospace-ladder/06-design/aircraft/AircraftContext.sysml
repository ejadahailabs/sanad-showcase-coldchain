// AircraftContext — RUN-04 aerospace ladder. Generated by tools/aero_model.py — edit there.
private import MrtmInterfaces::*;
private import MrtmSystemContext::*;
private import AeroPorts::*;
private import NodeAircraft::*;

package AircraftContext {

    doc /* The monitor among the things it touches (package-level parts so the canvas can place them, F-129). No satisfy here. */

    part fridge : Fridge;
    part monitor : MonitorDevice;
    part mains : MainsSupply;
    part usbHost : UsbHost;
    part staff : Staff;
    interface airContact : ThermalContact connect fridge.air to monitor.air;
    interface mainsFeed : PowerFeed connect mains.output to monitor.mains;
    interface historyLink : UsbLink connect monitor.usb to usbHost.usb;
    connect monitor.alarmSignals to staff.alarmSignals;
    connect monitor.screen to staff.screen;
}
