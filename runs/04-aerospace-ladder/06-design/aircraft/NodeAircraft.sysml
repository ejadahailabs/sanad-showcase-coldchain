// NodeAircraft — RUN-04 aerospace ladder. Generated by tools/aero_model.py — edit there.
private import ScalarValues::*;
private import ProjectRequirements::*;
private import MrtmInterfaces::*;
private import AeroPorts::*;

package NodeAircraft {

    doc /* AIRCRAFT LEVEL (ARP4754A §5.1): the monitor as ONE product among its neighbours, and its five functions. Covers the stakeholder needs, the product functions and the FHA safety objectives only. */

    part def MonitorDevice {
        doc /* The product seen from outside: what the clinic touches. DAL A (FHA, 08-safety/01-fha.md). */
        port air : ~ThermalPort;
        port mains : ~PowerPort;
        port usb : UsbPort;
        port alarmSignals : AlarmHmiPort;
        port screen : ScreenPort;
    }
    part monitor : MonitorDevice;

    satisfy 'MRTM-FUN-001' by monitor;
    satisfy 'MRTM-FUN-002' by monitor;
    satisfy 'MRTM-FUN-003' by monitor;
    satisfy 'MRTM-FUN-004' by monitor;
    satisfy 'MRTM-FUN-005' by monitor;
    satisfy 'MRTM-SOB-001' by monitor;
    satisfy 'MRTM-SOB-002' by monitor;
    satisfy 'MRTM-SOB-003' by monitor;
    satisfy 'MRTM-SOB-004' by monitor;
    satisfy 'MRTM-SOB-005' by monitor;
    satisfy 'MRTM-STK-001' by monitor;
    satisfy 'MRTM-STK-002' by monitor;
    satisfy 'MRTM-STK-003' by monitor;
    satisfy 'MRTM-STK-004' by monitor;
    satisfy 'MRTM-STK-005' by monitor;
    satisfy 'MRTM-STK-006' by monitor;
    satisfy 'MRTM-STK-007' by monitor;
    satisfy 'MRTM-STK-008' by monitor;
}
