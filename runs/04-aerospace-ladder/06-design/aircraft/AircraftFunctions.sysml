// AircraftFunctions — RUN-04 aerospace ladder. Generated by tools/aero_model.py — edit there.
private import MrtmInterfaces::*;

package AircraftFunctions {

    doc /* The five product functions (ARP4754A aircraft-level functions): MRTM-FUN-001…005. The FHA asks of each how it can fail. */

    action def ProductFunctions {
        action monitorAir { doc /* MRTM-FUN-001 */ out item sample : TemperatureSample; }
        action warnExcursion { doc /* MRTM-FUN-002 */ in item sample : TemperatureSample; out item excursion : ExcursionState; }
        action acknowledgeWarning { doc /* MRTM-FUN-003 */ in item excursion : ExcursionState; }
        action keepHistory { doc /* MRTM-FUN-004 */ in item excursion : ExcursionState; }
        action watchThroughPowerCut { doc /* MRTM-FUN-005 */ out item power : PowerEvent; }
        flow of TemperatureSample from monitorAir.sample to warnExcursion.sample;
        flow of ExcursionState from warnExcursion.excursion to acknowledgeWarning.excursion;
        flow of ExcursionState from warnExcursion.excursion to keepHistory.excursion;
        succession first monitorAir then warnExcursion;
    }
}
