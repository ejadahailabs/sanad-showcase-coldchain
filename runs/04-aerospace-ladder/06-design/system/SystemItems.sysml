// SystemItems — RUN-04 aerospace ladder. Generated by tools/aero_model.py — edit there.
private import AeroPorts::*;
private import NodeSensorHw::*;
private import NodeAlarmHw::*;
private import NodeControllerHw::*;
private import NodePowerHw::*;
private import NodeDisplayHw::*;
private import NodeAlarmSw::*;
private import NodePlatformSw::*;
private import NodeDisplaySw::*;
private import NodeRecordSw::*;
private import NodeExportSw::*;

package SystemItems {

    doc /* The ten items of the system and their DAL, as one tree (item block view). No satisfy here. */

    part def MonitorSystemItems {
        part sensorHw : SensorHw;
        part alarmHw : AlarmHw;
        part controllerHw : ControllerHw;
        part powerHw : PowerHw;
        part displayHw : DisplayHw;
        part alarmSw : AlarmSw;
        part platformSw : PlatformSw;
        part displaySw : DisplaySw;
        part recordSw : RecordSw;
        part exportSw : ExportSw;
    }
}
