// SystemSoftware — RUN-04 aerospace ladder. Generated by tools/aero_model.py — edit there.
private import AeroPorts::*;
private import NodeAlarmSw::*;
private import NodePlatformSw::*;
private import NodeDisplaySw::*;
private import NodeRecordSw::*;
private import NodeExportSw::*;

package SystemSoftware {

    doc /* Software item interconnection: the five software items and the flows between them (all hosted on the controller hardware). No satisfy here. */

    part alarmSw : AlarmSw;
    part platformSw : PlatformSw;
    part displaySw : DisplaySw;
    part recordSw : RecordSw;
    part exportSw : ExportSw;
    connect alarmSw.samples to displaySw.samples;
    connect alarmSw.alarmState to displaySw.alarmState;
    connect alarmSw.records to recordSw.records;
    connect platformSw.records to recordSw.records;
    connect alarmSw.heartbeat to platformSw.heartbeat;
    connect platformSw.band to alarmSw.band;
    connect platformSw.powerEvents to alarmSw.powerEvents;
    connect recordSw.history to exportSw.history;
}
