// NodeSystem — RUN-04 aerospace ladder. Generated by tools/aero_model.py — edit there.
private import ScalarValues::*;
private import ProjectRequirements::*;
private import MrtmInterfaces::*;
private import AeroPorts::*;
private import NodeAircraft::*;
private import NodeSensorHw::*;
private import NodeAlarmHw::*;
private import NodeControllerHw::*;
private import NodePowerHw::*;
private import NodeDisplayHw::*;
private import NodeAlarmSw::*;
private import NodePlatformSw::*;
private import NodeDisplaySw::*;
private import NodeRecordSw::*;
private import NodeExportSw::*;

package NodeSystem {

    doc /* SYSTEM LEVEL (ARP4754A §5.2–5.3): the monitoring system and its ten items. Covers the system requirements only. */

    part def MonitorSystem :> MonitorDevice {
        doc /* The system: five hardware items, five software items hosted on the controller hardware. */
        part sensorHw : SensorHw;
        part alarmHw : AlarmHw;
        part controllerHw : ControllerHw;
        part powerHw : PowerHw;
        part displayHw : DisplayHw;
        part alarmSw : AlarmSw;
        part platformSw : PlatformSw;
        part displaySw : DisplaySw;
        part recordSw : RecordSw;
        part exportSw : ExportSw;
        allocate alarmSw to controllerHw;
        allocate platformSw to controllerHw;
        allocate displaySw to controllerHw;
        allocate recordSw to controllerHw;
        allocate exportSw to controllerHw;
    }
    part system : MonitorSystem;

    satisfy 'MRTM-ENV-001' by system;
    satisfy 'MRTM-ENV-002' by system;
    satisfy 'MRTM-ENV-003' by system;
    satisfy 'MRTM-ENV-004' by system;
    satisfy 'MRTM-IFC-001' by system;
    satisfy 'MRTM-IFC-002' by system;
    satisfy 'MRTM-IFC-003' by system;
    satisfy 'MRTM-IFC-004' by system;
    satisfy 'MRTM-MNT-001' by system;
    satisfy 'MRTM-MNT-002' by system;
    satisfy 'MRTM-MNT-003' by system;
    satisfy 'MRTM-PRF-001' by system;
    satisfy 'MRTM-PRF-002' by system;
    satisfy 'MRTM-PRF-003' by system;
    satisfy 'MRTM-PRF-004' by system;
    satisfy 'MRTM-SAF-001' by system;
    satisfy 'MRTM-SAF-002' by system;
    satisfy 'MRTM-SAF-003' by system;
    satisfy 'MRTM-SAF-004' by system;
    satisfy 'MRTM-SAF-005' by system;
    satisfy 'MRTM-SAF-006' by system;
    satisfy 'MRTM-SAF-007' by system;
    satisfy 'MRTM-SAF-008' by system;
    satisfy 'MRTM-SAF-009' by system;
    satisfy 'MRTM-SAF-010' by system;
    satisfy 'MRTM-SAF-011' by system;
    satisfy 'MRTM-SAF-012' by system;
    satisfy 'MRTM-SAF-013' by system;
    satisfy 'MRTM-SAF-014' by system;
    satisfy 'MRTM-SAF-015' by system;
    satisfy 'MRTM-SAF-016' by system;
    satisfy 'MRTM-SAF-017' by system;
    satisfy 'MRTM-SAF-018' by system;
    satisfy 'MRTM-SAF-019' by system;
    satisfy 'MRTM-SAF-020' by system;
    satisfy 'MRTM-SAF-021' by system;
    satisfy 'MRTM-SAF-022' by system;
    satisfy 'MRTM-SAF-023' by system;
    satisfy 'MRTM-SYS-001' by system;
    satisfy 'MRTM-SYS-002' by system;
    satisfy 'MRTM-SYS-003' by system;
    satisfy 'MRTM-SYS-004' by system;
    satisfy 'MRTM-SYS-005' by system;
    satisfy 'MRTM-SYS-006' by system;
    satisfy 'MRTM-SYS-007' by system;
    satisfy 'MRTM-SYS-008' by system;
    satisfy 'MRTM-SYS-009' by system;
    satisfy 'MRTM-SYS-010' by system;
    satisfy 'MRTM-SYS-011' by system;
    satisfy 'MRTM-SYS-012' by system;
    satisfy 'MRTM-SYS-013' by system;
    satisfy 'MRTM-SYS-014' by system;
    satisfy 'MRTM-SYS-015' by system;
    satisfy 'MRTM-SYS-016' by system;
    satisfy 'MRTM-SYS-017' by system;
    satisfy 'MRTM-SYS-018' by system;
    satisfy 'MRTM-SYS-019' by system;
    satisfy 'MRTM-SYS-020' by system;
    satisfy 'MRTM-SYS-021' by system;
    satisfy 'MRTM-SYS-022' by system;
    satisfy 'MRTM-SYS-023' by system;
    satisfy 'MRTM-SYS-024' by system;
}
