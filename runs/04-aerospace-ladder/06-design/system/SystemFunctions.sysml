// SystemFunctions — RUN-04 aerospace ladder. Generated by tools/aero_model.py — edit there.
private import MrtmInterfaces::*;

package SystemFunctions {

    doc /* Functional decomposition at SYSTEM level: the nine system functions the items perform (from run 2's MrtmLogical, without the performers). No satisfy here. */

    action def MonitoringFunctions {
        action acquireSample { doc /* sensor-hw, alarm-sw */ out item sample : TemperatureSample; }
        action checkProbe { doc /* alarm-sw */ in item sample : TemperatureSample; out item valid : TemperatureSample; }
        action detectExcursion { doc /* alarm-sw */ in item valid : TemperatureSample; out item excursion : ExcursionState; }
        action annunciateAlarm { doc /* alarm-sw, alarm-hw */ in item excursion : ExcursionState; out item command : AlarmCommand; }
        action showStatus { doc /* display-sw, display-hw */ in item excursion : ExcursionState; }
        action recordEvent { doc /* record-sw */ in item excursion : ExcursionState; in item power : PowerEvent; out item record : LogRecord; }
        action serveHistory { doc /* export-sw */ in item record : LogRecord; }
        action supervisePower { doc /* power-hw, platform-sw */ out item power : PowerEvent; }
        action superviseSoftware { doc /* platform-sw, controller-hw, backup alarm */ }
        flow of TemperatureSample from acquireSample.sample to checkProbe.sample;
        flow of TemperatureSample from checkProbe.valid to detectExcursion.valid;
        flow of ExcursionState from detectExcursion.excursion to annunciateAlarm.excursion;
        flow of ExcursionState from detectExcursion.excursion to showStatus.excursion;
        flow of ExcursionState from detectExcursion.excursion to recordEvent.excursion;
        flow of PowerEvent from supervisePower.power to recordEvent.power;
        flow of LogRecord from recordEvent.record to serveHistory.record;
    }
}
