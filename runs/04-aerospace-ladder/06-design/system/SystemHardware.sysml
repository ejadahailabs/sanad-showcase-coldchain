// SystemHardware — RUN-04 aerospace ladder. Generated by tools/aero_model.py — edit there.
private import MrtmInterfaces::*;
private import MrtmSystemContext::*;
private import AeroPorts::*;
private import NodeSensorHw::*;
private import NodeAlarmHw::*;
private import NodeControllerHw::*;
private import NodePowerHw::*;
private import NodeDisplayHw::*;

package SystemHardware {

    doc /* Hardware item interconnection: the five hardware items, their buses and lines, and the neighbours the boundary meets (package-level parts, F-129). No satisfy here. */

    part sensorHw : SensorHw;
    part controllerHw : ControllerHw;
    part alarmHw : AlarmHw;
    part displayHw : DisplayHw;
    part powerHw : PowerHw;
    part fridge : Fridge;
    part mains : MainsSupply;
    part staff : Staff;
    interface airContact : ThermalContact connect fridge.air to sensorHw.air;
    interface probeBus : ProbeBus connect controllerHw.probeBus to sensorHw.bus;
    interface displayBus : I2cBus connect controllerHw.i2c to displayHw.i2c;
    interface buzzerLine : SignalLine connect controllerHw.buzzerDrive to alarmHw.buzzerDrive;
    interface ledLine : SignalLine connect controllerHw.redLed to alarmHw.redLed;
    interface watchdogLine : SignalLine connect controllerHw.wdtPulse to alarmHw.wdtPulse;
    interface ackLine : ButtonLine connect controllerHw.ack to alarmHw.ack;
    interface currentSense : SenseLine connect controllerHw.buzzerSense to alarmHw.buzzerSense;
    interface mainsSense : SenseLine connect controllerHw.mainsSense to powerHw.mainsSense;
    interface mainsFeed : PowerFeed connect mains.output to powerHw.mains;
    interface boardFeed : PowerFeed connect powerHw.supply to controllerHw.supply;
    interface alarmFeed : PowerFeed connect powerHw.supply to alarmHw.supply;
    interface displayFeed : PowerFeed connect powerHw.supply to displayHw.supply;
    connect alarmHw.alarmSignals to staff.alarmSignals;
    connect displayHw.screen to staff.screen;
}
