// AlarmPathSequence — RUN-04 aerospace ladder. Generated by tools/aero_model.py — edit there.
private import MrtmInterfaces::*;
private import MrtmSystemContext::*;
private import AeroPorts::*;
private import NodeSensorHw::*;
private import NodeAlarmSw::*;
private import NodeAlarmHw::*;
private import NodeRecordSw::*;

package AlarmPathSequence {

    doc /* The alarm path at ITEM granularity: warm air → sensor hardware → alarm software (early light, then 31 samples / 60 s, then buzzer) → alarm hardware → staff; the record software logs it. Budgets: sample 2 s + conversion 0.75 s + one 1 s alarm cycle ≤ 5 s (ADR-0030). Timing is text only (run 2 F-123). */

    part fridge : Fridge;
    part sensorHw : SensorHw;
    part alarmSw : AlarmSw;
    part alarmHw : AlarmHw;
    part recordSw : RecordSw;
    part staff : Staff;
    message warmAir of AirHeat from fridge to sensorHw;
    message sample of TemperatureSample from sensorHw to alarmSw;
    message earlyDrive of LowPriorityLight from alarmSw to alarmHw;
    message earlyLight of LowPriorityLight from alarmHw to staff;
    message buzzerDrive of ExcursionSound from alarmSw to alarmHw;
    message sounding of ExcursionSound from alarmHw to staff;
    message logStart of LogRecord from alarmSw to recordSw;
    message acknowledge of ButtonPress from staff to alarmHw;
    message ackLine of ButtonPress from alarmHw to alarmSw;
    message silence of AudioPaused from alarmSw to alarmHw;
    succession first warmAir then sample;
    succession first sample then earlyDrive;
    succession first earlyDrive then earlyLight;
    succession first earlyLight then buzzerDrive;
    succession first buzzerDrive then sounding;
    succession first sounding then logStart;
    succession first logStart then acknowledge;
    succession first acknowledge then ackLine;
    succession first ackLine then silence;
}
