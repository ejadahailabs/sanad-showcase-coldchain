package System_softwareView {

    comment /* A view file. It imports the packages it draws, exposes elements and names a
       rendering; it declares nothing of the model. Delete it and every package file is
       byte-identical and the model reads unchanged. */

    private import SystemSoftware::*;
    private import SanadRenderings::*;

    view 'system_software' : StandardViewDefinitions::InterconnectionView {
        expose SystemSoftware::**;
        render asInterconnectionView;
    }
}

package 'Layout_Sanad' {

    comment /* Layout only. Written and read by this workbench.
       Every entry annotates an element by qualified name; no model element is modified.
       Delete this package and the model is unchanged. */

    private import ScalarValues::*;

    metadata def 'Layout' {
        attribute 'viewName' : String;
        attribute 'x' : Real;
        attribute 'y' : Real;
        attribute 'w' : Real;
        attribute 'h' : Real;
    }

    metadata def 'EdgeLayout' {
        attribute 'viewName' : String;
        attribute 'edge' : String;
        attribute 'bends' : String;
    }

    metadata def 'PlainBoxes' {
        attribute 'viewName' : String;
    }

    metadata 'l1' : 'Layout' about 'SystemSoftware'::'alarmSw' {
        'viewName' = "system_software";
        'x' = 380;
        'y' = 40;
    }

    metadata 'l2' : 'Layout' about 'SystemSoftware'::'displaySw' {
        'viewName' = "system_software";
        'x' = 760;
        'y' = 40;
    }

    metadata 'l3' : 'Layout' about 'SystemSoftware'::'exportSw' {
        'viewName' = "system_software";
        'x' = 760;
        'y' = 400;
    }

    metadata 'l4' : 'Layout' about 'SystemSoftware'::'platformSw' {
        'viewName' = "system_software";
        'x' = 20;
        'y' = 220;
    }

    metadata 'l5' : 'Layout' about 'SystemSoftware'::'recordSw' {
        'viewName' = "system_software";
        'x' = 380;
        'y' = 400;
    }

    metadata 'p1' : 'PlainBoxes' {
        'viewName' = "system_software";
    }
}
