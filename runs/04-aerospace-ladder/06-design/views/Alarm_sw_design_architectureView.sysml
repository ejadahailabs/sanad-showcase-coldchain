package Alarm_sw_design_architectureView {

    comment /* A view file. It imports the packages it draws, exposes elements and names a
       rendering; it declares nothing of the model. Delete it and every package file is
       byte-identical and the model reads unchanged. */

    private import AlarmSwArchitecture::*;
    private import SanadRenderings::*;

    view 'alarm_sw_design_architecture' : StandardViewDefinitions::GeneralView {
        expose AlarmSwArchitecture::**;
        render asGeneralView;
    }
}
