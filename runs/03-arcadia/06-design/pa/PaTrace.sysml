// PaTrace — layer `pa` (Physical Architecture) of .ejadah/rew/framework.yaml. Generated by tools/arcadia.py satisfy — edit there.
// Covers ONLY this layer's requirements (36): rule `satisfy: own-layer-only`.
private import ProjectRequirements::*;

package PaTrace {
    satisfy 'MRTM-PH-001' by PaInterconnection::backupAlarm;
    satisfy 'MRTM-PH-002' by PaInterconnection::backupAlarm;
    satisfy 'MRTM-PH-003' by PaBackupAlarm::driver;
    satisfy 'MRTM-PH-004' by PaBackupAlarm::timer;
    satisfy 'MRTM-PH-005' by PaBackupAlarm::holdUp;
    satisfy 'MRTM-PH-006' by PaInterconnection::buzzer;
    satisfy 'MRTM-PH-007' by PaInterconnection::indicators;
    satisfy 'MRTM-PH-008' by PaInterconnection::indicators;
    satisfy 'MRTM-PH-009' by PaInterconnection::oled;
    satisfy 'MRTM-PH-010' by PaInterconnection::rtc;
    satisfy 'MRTM-PH-011' by PaInterconnection::battery;
    satisfy 'MRTM-PH-012' by PaInterconnection::powerPath;
    satisfy 'MRTM-PH-013' by PaInterconnection::probe;
    satisfy 'MRTM-PH-014' by PaInterconnection::probe;
    satisfy 'MRTM-PH-015' by PaInterconnection::probe;
    satisfy 'MRTM-PH-016' by PaInterconnection::mcu;
    satisfy 'MRTM-SW-001' by PaSoftware::alarmItem;
    satisfy 'MRTM-SW-002' by PaSoftware::alarmItem;
    satisfy 'MRTM-SW-003' by PaSoftware::alarmItem;
    satisfy 'MRTM-SW-004' by PaSoftware::alarmItem;
    satisfy 'MRTM-SW-005' by PaSoftware::excursionItem;
    satisfy 'MRTM-SW-006' by PaSoftware::excursionItem;
    satisfy 'MRTM-SW-007' by PaSoftware::excursionItem;
    satisfy 'MRTM-SW-008' by PaSoftware::displayItem;
    satisfy 'MRTM-SW-009' by PaSoftware::displayItem;
    satisfy 'MRTM-SW-010' by PaSoftware::logItem;
    satisfy 'MRTM-SW-011' by PaSoftware::logItem;
    satisfy 'MRTM-SW-012' by PaSoftware::usbItem;
    satisfy 'MRTM-SW-013' by PaSoftware::usbItem;
    satisfy 'MRTM-SW-014' by PaSoftware::powerItem;
    satisfy 'MRTM-SW-015' by PaSoftware::powerItem;
    satisfy 'MRTM-SW-016' by PaSoftware::sensorItem;
    satisfy 'MRTM-SW-017' by PaSoftware::sensorItem;
    satisfy 'MRTM-SW-018' by PaSoftware::supervisorItem;
    satisfy 'MRTM-SW-019' by PaSoftware::supervisorItem;
    satisfy 'MRTM-SW-020' by PaSoftware::supervisorItem;
}
