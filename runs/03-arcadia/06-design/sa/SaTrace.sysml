// SaTrace — layer `sa` (System Analysis) of .ejadah/rew/framework.yaml. Generated by tools/arcadia.py satisfy — edit there.
// Covers ONLY this layer's requirements (62): rule `satisfy: own-layer-only`.
private import ProjectRequirements::*;

package SaTrace {
    satisfy 'MRTM-ENV-001' by SaFunctions::keepPowered;
    satisfy 'MRTM-ENV-002' by SaContext::monitor;
    satisfy 'MRTM-ENV-003' by SaContext::monitor;
    satisfy 'MRTM-ENV-004' by SaFunctions::acquireTemperature;
    satisfy 'MRTM-IFC-001' by SaFunctions::acquireTemperature;
    satisfy 'MRTM-IFC-002' by SaFunctions::announceAlarm;
    satisfy 'MRTM-IFC-003' by SaFunctions::exportHistory;
    satisfy 'MRTM-IFC-004' by SaFunctions::showStatus;
    satisfy 'MRTM-MNT-001' by SaFunctions::acquireTemperature;
    satisfy 'MRTM-MNT-002' by SaFunctions::keepPowered;
    satisfy 'MRTM-MNT-003' by SaFunctions::superviseItself;
    satisfy 'MRTM-PRF-001' by SaFunctions::acquireTemperature;
    satisfy 'MRTM-PRF-002' by SaFunctions::announceAlarm;
    satisfy 'MRTM-PRF-003' by SaFunctions::exportHistory;
    satisfy 'MRTM-PRF-004' by SaFunctions::showStatus;
    satisfy 'MRTM-SAF-001' by SaFunctions::announceAlarm;
    satisfy 'MRTM-SAF-002' by SaFunctions::announceAlarm;
    satisfy 'MRTM-SAF-003' by SaFunctions::acquireTemperature;
    satisfy 'MRTM-SAF-004' by SaFunctions::superviseItself;
    satisfy 'MRTM-SAF-005' by SaFunctions::keepPowered;
    satisfy 'MRTM-SAF-006' by SaFunctions::superviseItself;
    satisfy 'MRTM-SAF-007' by SaFunctions::superviseItself;
    satisfy 'MRTM-SAF-008' by SaFunctions::keepPowered;
    satisfy 'MRTM-SAF-009' by SaFunctions::alarmOnOwnFailure;
    satisfy 'MRTM-SAF-010' by SaFunctions::superviseItself;
    satisfy 'MRTM-SAF-011' by SaFunctions::announceAlarm;
    satisfy 'MRTM-SAF-012' by SaFunctions::showStatus;
    satisfy 'MRTM-SAF-013' by SaFunctions::alarmOnOwnFailure;
    satisfy 'MRTM-SAF-014' by SaFunctions::announceAlarm;
    satisfy 'MRTM-SAF-015' by SaFunctions::announceAlarm;
    satisfy 'MRTM-SAF-016' by SaFunctions::showStatus;
    satisfy 'MRTM-SAF-017' by SaFunctions::superviseItself;
    satisfy 'MRTM-SAF-018' by SaFunctions::recordEvents;
    satisfy 'MRTM-SAF-019' by SaFunctions::announceAlarm;
    satisfy 'MRTM-SAF-020' by SaFunctions::acquireTemperature;
    satisfy 'MRTM-SAF-021' by SaFunctions::showStatus;
    satisfy 'MRTM-SAF-022' by SaFunctions::recordEvents;
    satisfy 'MRTM-SAF-023' by SaFunctions::superviseItself;
    satisfy 'MRTM-SYS-001' by SaFunctions::acquireTemperature;
    satisfy 'MRTM-SYS-002' by SaFunctions::detectExcursion;
    satisfy 'MRTM-SYS-003' by SaFunctions::announceAlarm;
    satisfy 'MRTM-SYS-004' by SaFunctions::announceAlarm;
    satisfy 'MRTM-SYS-005' by SaFunctions::showStatus;
    satisfy 'MRTM-SYS-006' by SaFunctions::announceAlarm;
    satisfy 'MRTM-SYS-007' by SaFunctions::showStatus;
    satisfy 'MRTM-SYS-008' by SaFunctions::recordEvents;
    satisfy 'MRTM-SYS-009' by SaFunctions::recordEvents;
    satisfy 'MRTM-SYS-010' by SaFunctions::recordEvents;
    satisfy 'MRTM-SYS-011' by SaFunctions::showStatus;
    satisfy 'MRTM-SYS-012' by SaFunctions::acquireTemperature;
    satisfy 'MRTM-SYS-013' by SaFunctions::showStatus;
    satisfy 'MRTM-SYS-014' by SaFunctions::exportHistory;
    satisfy 'MRTM-SYS-015' by SaFunctions::recordEvents;
    satisfy 'MRTM-SYS-016' by SaFunctions::keepPowered;
    satisfy 'MRTM-SYS-017' by SaFunctions::detectExcursion;
    satisfy 'MRTM-SYS-018' by SaFunctions::detectExcursion;
    satisfy 'MRTM-SYS-019' by SaFunctions::announceAlarm;
    satisfy 'MRTM-SYS-020' by SaFunctions::recordEvents;
    satisfy 'MRTM-SYS-021' by SaFunctions::recordEvents;
    satisfy 'MRTM-SYS-022' by SaFunctions::showStatus;
    satisfy 'MRTM-SYS-023' by SaFunctions::keepPowered;
    satisfy 'MRTM-SYS-024' by SaFunctions::detectExcursion;
}
