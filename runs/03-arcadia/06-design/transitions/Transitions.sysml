// Transitions (Arcadia): one `allocate` per element, one package per layer pair. Generated by tools/arcadia.py transitions.
// Read by tools/level-check.py (rule `transitions: complete`); tables in the .md files beside this one.

package TransitionOaToSa {
    doc /* Operational Analysis → System Analysis: operational activity → system function. */
    allocate OaModel::storeVaccinesCold to SaContext::fridge;
    allocate OaModel::watchFridgeTemperature to SaFunctions::acquireTemperature;
    allocate OaModel::watchFridgeTemperature to SaFunctions::detectExcursion;
    allocate OaModel::watchFridgeTemperature to SaFunctions::showStatus;
    allocate OaModel::respondToWarmFridge to SaFunctions::announceAlarm;
    allocate OaModel::respondToWarmFridge to SaFunctions::alarmOnOwnFailure;
    allocate OaModel::respondToWarmFridge to SaContext::staff;
    allocate OaModel::auditStorageHistory to SaFunctions::recordEvents;
    allocate OaModel::auditStorageHistory to SaFunctions::exportHistory;
    allocate OaModel::auditStorageHistory to SaContext::recordsComputer;
    allocate OaModel::serviceMeasuringEquipment to SaFunctions::superviseItself;
    allocate OaModel::serviceMeasuringEquipment to SaContext::staff;
    allocate OaModel::rideThroughPowerCut to SaFunctions::keepPowered;
    allocate OaModel::rideThroughPowerCut to SaContext::mains;
    allocate OaArchitecture::fridge to SaContext::fridge;
    allocate OaArchitecture::stock to SaContext::fridge;
    allocate OaArchitecture::nurse to SaContext::staff;
    allocate OaArchitecture::manager to SaContext::staff;
    allocate OaArchitecture::technician to SaContext::staff;
    allocate OaArchitecture::mains to SaContext::mains;
}

package TransitionSaToLa {
    doc /* System Analysis → Logical Architecture: system function → logical component. */
    allocate SaFunctions::acquireTemperature to LaArchitecture::sensing;
    allocate SaFunctions::detectExcursion to LaArchitecture::alarm;
    allocate SaFunctions::announceAlarm to LaArchitecture::alarm;
    allocate SaFunctions::alarmOnOwnFailure to LaArchitecture::alarm;
    allocate SaFunctions::showStatus to LaArchitecture::display;
    allocate SaFunctions::recordEvents to LaArchitecture::logging;
    allocate SaFunctions::exportHistory to LaArchitecture::logging;
    allocate SaFunctions::keepPowered to LaArchitecture::power;
    allocate SaFunctions::superviseItself to LaArchitecture::supervision;
}

package TransitionLaToPa {
    doc /* Logical Architecture → Physical Architecture: logical component → physical / behaviour component. */
    allocate LaArchitecture::sensing to PaInterconnection::probe;
    allocate LaArchitecture::sensing to PaSoftware::sensorItem;
    allocate LaArchitecture::alarm to PaSoftware::excursionItem;
    allocate LaArchitecture::alarm to PaSoftware::alarmItem;
    allocate LaArchitecture::alarm to PaInterconnection::buzzer;
    allocate LaArchitecture::alarm to PaInterconnection::indicators;
    allocate LaArchitecture::alarm to PaInterconnection::backupAlarm;
    allocate LaArchitecture::display to PaInterconnection::oled;
    allocate LaArchitecture::display to PaSoftware::displayItem;
    allocate LaArchitecture::logging to PaInterconnection::rtc;
    allocate LaArchitecture::logging to PaSoftware::logItem;
    allocate LaArchitecture::logging to PaSoftware::usbItem;
    allocate LaArchitecture::power to PaInterconnection::battery;
    allocate LaArchitecture::power to PaInterconnection::powerPath;
    allocate LaArchitecture::power to PaSoftware::powerItem;
    allocate LaArchitecture::supervision to PaInterconnection::mcu;
    allocate LaArchitecture::supervision to PaSoftware::supervisorItem;
}

package TransitionPaToEpbs {
    doc /* Physical Architecture → End-Product Breakdown Structure: physical / behaviour component → configuration item. */
    allocate PaSoftware::sensorItem to EpbsBreakdown::product.firmwareImage;
    allocate PaSoftware::excursionItem to EpbsBreakdown::product.firmwareImage;
    allocate PaSoftware::alarmItem to EpbsBreakdown::product.firmwareImage;
    allocate PaSoftware::displayItem to EpbsBreakdown::product.firmwareImage;
    allocate PaSoftware::logItem to EpbsBreakdown::product.firmwareImage;
    allocate PaSoftware::usbItem to EpbsBreakdown::product.firmwareImage;
    allocate PaSoftware::powerItem to EpbsBreakdown::product.firmwareImage;
    allocate PaSoftware::supervisorItem to EpbsBreakdown::product.firmwareImage;
    allocate PaInterconnection::mcu to EpbsBreakdown::product.mainBoard;
    allocate PaInterconnection::rtc to EpbsBreakdown::product.mainBoard;
    allocate PaInterconnection::indicators to EpbsBreakdown::product.mainBoard;
    allocate PaInterconnection::buzzer to EpbsBreakdown::product.mainBoard;
    allocate PaInterconnection::powerPath to EpbsBreakdown::product.mainBoard;
    allocate PaInterconnection::probe to EpbsBreakdown::product.probeAssembly;
    allocate PaInterconnection::oled to EpbsBreakdown::product.displayModule;
    allocate PaInterconnection::backupAlarm to EpbsBreakdown::product.backupAlarmBoard;
    allocate PaBackupAlarm::timer to EpbsBreakdown::product.backupAlarmBoard;
    allocate PaBackupAlarm::driver to EpbsBreakdown::product.backupAlarmBoard;
    allocate PaBackupAlarm::holdUp to EpbsBreakdown::product.backupAlarmBoard;
    allocate PaInterconnection::battery to EpbsBreakdown::product.batteryPack;
}
