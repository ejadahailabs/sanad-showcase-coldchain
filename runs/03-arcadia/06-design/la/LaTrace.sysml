// LaTrace — layer `la` (Logical Architecture) of .ejadah/rew/framework.yaml. Generated by tools/arcadia.py satisfy — edit there.
// Covers ONLY this layer's requirements (26): rule `satisfy: own-layer-only`.
private import ProjectRequirements::*;

package LaTrace {
    satisfy 'MRTM-LA-001' by LaArchitecture::alarm;
    satisfy 'MRTM-LA-002' by LaArchitecture::alarm;
    satisfy 'MRTM-LA-003' by LaArchitecture::alarm;
    satisfy 'MRTM-LA-004' by LaArchitecture::alarm;
    satisfy 'MRTM-LA-005' by LaArchitecture::alarm;
    satisfy 'MRTM-LA-006' by LaArchitecture::alarm;
    satisfy 'MRTM-LA-007' by LaArchitecture::alarm;
    satisfy 'MRTM-LA-008' by LaArchitecture::alarm;
    satisfy 'MRTM-LA-009' by LaArchitecture::display;
    satisfy 'MRTM-LA-010' by LaArchitecture::display;
    satisfy 'MRTM-LA-011' by LaArchitecture::display;
    satisfy 'MRTM-LA-012' by LaArchitecture::logging;
    satisfy 'MRTM-LA-013' by LaArchitecture::logging;
    satisfy 'MRTM-LA-014' by LaArchitecture::logging;
    satisfy 'MRTM-LA-015' by LaArchitecture::logging;
    satisfy 'MRTM-LA-016' by LaArchitecture::power;
    satisfy 'MRTM-LA-017' by LaArchitecture::power;
    satisfy 'MRTM-LA-018' by LaArchitecture::power;
    satisfy 'MRTM-LA-019' by LaArchitecture::sensing;
    satisfy 'MRTM-LA-020' by LaArchitecture::sensing;
    satisfy 'MRTM-LA-021' by LaArchitecture::sensing;
    satisfy 'MRTM-LA-022' by LaArchitecture::sensing;
    satisfy 'MRTM-LA-023' by LaArchitecture::supervision;
    satisfy 'MRTM-LA-024' by LaArchitecture::supervision;
    satisfy 'MRTM-LA-025' by LaArchitecture::supervision;
    satisfy 'MRTM-LA-026' by LaArchitecture::supervision;
}
