// OaTrace — layer `oa` (Operational Analysis) of .ejadah/rew/framework.yaml. Generated by tools/arcadia.py satisfy — edit there.
// Covers ONLY this layer's requirements (8): rule `satisfy: own-layer-only`.
private import ProjectRequirements::*;

package OaTrace {
    satisfy 'MRTM-STK-001' by OaCapabilities::knowTheFridgeIsSafe;
    satisfy 'MRTM-STK-002' by OaCapabilities::knowTheFridgeIsSafe;
    satisfy 'MRTM-STK-003' by OaCapabilities::respondToAnExcursion;
    satisfy 'MRTM-STK-004' by OaCapabilities::knowTheFridgeIsSafe;
    satisfy 'MRTM-STK-005' by OaCapabilities::proveTheStorageHistory;
    satisfy 'MRTM-STK-006' by OaCapabilities::proveTheStorageHistory;
    satisfy 'MRTM-STK-007' by OaCapabilities::trustTheWatching;
    satisfy 'MRTM-STK-008' by OaCapabilities::trustTheWatching;
}
