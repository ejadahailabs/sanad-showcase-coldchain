package ReqEPBS {
    comment /* GENERATED from the Markdown requirement corpus at 36043191add0578d.
       Read-only: edit the Markdown requirement, not this file. Sanad regenerates it on
       every corpus change and the same corpus always gives byte-identical text. */

    requirement <'MRTM-CI-001'> MRTM_CI_001 {
        doc /* The firmware configuration item shall carry 1 version number, identical in its release record and on the power-up screen. */
    }

    requirement <'MRTM-CI-002'> MRTM_CI_002 {
        doc /* The main board configuration item shall carry a label with 1 part number and 1 revision that match its bill of materials entry. */
    }

    requirement <'MRTM-CI-003'> MRTM_CI_003 {
        doc /* The probe configuration item shall carry a cable label with 1 part number and 1 revision that match its bill of materials entry. */
    }

    requirement <'MRTM-CI-004'> MRTM_CI_004 {
        doc /* The display configuration item shall carry a label with 1 part number and 1 revision that match its bill of materials entry. */
    }

    requirement <'MRTM-CI-005'> MRTM_CI_005 {
        doc /* The backup alarm configuration item shall carry a label with 1 part number and 1 revision that match its bill of materials entry. */
    }

    requirement <'MRTM-CI-006'> MRTM_CI_006 {
        doc /* The battery configuration item shall carry a label with 1 part number, 1 revision and 1 date code that match its bill of materials entry. */
    }
}
