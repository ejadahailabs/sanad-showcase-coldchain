package Pa_backup_alarmView {

    comment /* A view file. It imports the packages it draws, exposes elements and names a
       rendering; it declares nothing of the model. Delete it and every package file is
       byte-identical and the model reads unchanged. */

    private import PaBackupAlarm::*;
    private import SanadRenderings::*;

    view 'pa_backup_alarm' : StandardViewDefinitions::InterconnectionView {
        expose PaBackupAlarm::**;
        render asInterconnectionView;
    }
}

package 'Layout_Sanad' {

    comment /* Layout only. Written and read by this workbench.
       Every entry annotates an element by qualified name; no model element is modified.
       Delete this package and the model is unchanged. */

    private import ScalarValues::*;

    metadata def 'Layout' {
        attribute 'viewName' : String;
        attribute 'x' : Real;
        attribute 'y' : Real;
        attribute 'w' : Real;
        attribute 'h' : Real;
    }

    metadata def 'EdgeLayout' {
        attribute 'viewName' : String;
        attribute 'edge' : String;
        attribute 'bends' : String;
    }

    metadata def 'PlainBoxes' {
        attribute 'viewName' : String;
    }

    metadata 'l1' : 'Layout' about 'PaBackupAlarm'::'buzzer' {
        'viewName' = "pa_backup_alarm";
        'x' = 1040;
        'y' = 40;
    }

    metadata 'l2' : 'Layout' about 'PaBackupAlarm'::'driver' {
        'viewName' = "pa_backup_alarm";
        'x' = 700;
        'y' = 40;
    }

    metadata 'l3' : 'Layout' about 'PaBackupAlarm'::'holdUp' {
        'viewName' = "pa_backup_alarm";
        'x' = 520;
        'y' = 320;
    }

    metadata 'l4' : 'Layout' about 'PaBackupAlarm'::'mcu' {
        'viewName' = "pa_backup_alarm";
        'x' = 20;
        'y' = 40;
    }

    metadata 'l5' : 'Layout' about 'PaBackupAlarm'::'powerPath' {
        'viewName' = "pa_backup_alarm";
        'x' = 20;
        'y' = 320;
    }

    metadata 'l6' : 'Layout' about 'PaBackupAlarm'::'timer' {
        'viewName' = "pa_backup_alarm";
        'x' = 360;
        'y' = 40;
    }

    metadata 'p1' : 'PlainBoxes' {
        'viewName' = "pa_backup_alarm";
    }
}
