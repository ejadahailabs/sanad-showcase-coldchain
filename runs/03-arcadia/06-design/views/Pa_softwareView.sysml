package Pa_softwareView {

    comment /* A view file. It imports the packages it draws, exposes elements and names a
       rendering; it declares nothing of the model. Delete it and every package file is
       byte-identical and the model reads unchanged. */

    private import PaInterconnection::*;
    private import PaSoftware::*;
    private import SanadRenderings::*;

    view 'pa_software' : StandardViewDefinitions::GeneralView {
        expose PaSoftware::**;
        expose PaInterconnection::mcu;
        render asGeneralView;
    }
}

package 'Layout_Sanad' {

    comment /* Layout only. Written and read by this workbench.
       Every entry annotates an element by qualified name; no model element is modified.
       Delete this package and the model is unchanged. */

    private import ScalarValues::*;

    metadata def 'Layout' {
        attribute 'viewName' : String;
        attribute 'x' : Real;
        attribute 'y' : Real;
        attribute 'w' : Real;
        attribute 'h' : Real;
    }

    metadata def 'EdgeLayout' {
        attribute 'viewName' : String;
        attribute 'edge' : String;
        attribute 'bends' : String;
    }

    metadata 'l1' : 'Layout' about 'PaInterconnection'::'mcu' {
        'viewName' = "pa_software";
        'x' = 420;
        'y' = 260;
    }

    metadata 'l2' : 'Layout' about 'PaSoftware'::'alarmItem' {
        'viewName' = "pa_software";
        'x' = 820;
        'y' = 20;
    }

    metadata 'l3' : 'Layout' about 'PaSoftware'::'displayItem' {
        'viewName' = "pa_software";
        'x' = 20;
        'y' = 380;
    }

    metadata 'l4' : 'Layout' about 'PaSoftware'::'excursionItem' {
        'viewName' = "pa_software";
        'x' = 420;
        'y' = 20;
    }

    metadata 'l5' : 'Layout' about 'PaSoftware'::'logItem' {
        'viewName' = "pa_software";
        'x' = 820;
        'y' = 380;
    }

    metadata 'l6' : 'Layout' about 'PaSoftware'::'powerItem' {
        'viewName' = "pa_software";
        'x' = 420;
        'y' = 740;
    }

    metadata 'l7' : 'Layout' about 'PaSoftware'::'sensorItem' {
        'viewName' = "pa_software";
        'x' = 20;
        'y' = 20;
    }

    metadata 'l8' : 'Layout' about 'PaSoftware'::'supervisorItem' {
        'viewName' = "pa_software";
        'x' = 820;
        'y' = 740;
    }

    metadata 'l9' : 'Layout' about 'PaSoftware'::'usbItem' {
        'viewName' = "pa_software";
        'x' = 20;
        'y' = 740;
    }
}
