// EpbsTrace — layer `epbs` (End-Product Breakdown Structure) of .ejadah/rew/framework.yaml. Generated by tools/arcadia.py satisfy — edit there.
// Covers ONLY this layer's requirements (6): rule `satisfy: own-layer-only`.
private import ProjectRequirements::*;

package EpbsTrace {
    satisfy 'MRTM-CI-001' by EpbsBreakdown::product.firmwareImage;
    satisfy 'MRTM-CI-002' by EpbsBreakdown::product.mainBoard;
    satisfy 'MRTM-CI-003' by EpbsBreakdown::product.probeAssembly;
    satisfy 'MRTM-CI-004' by EpbsBreakdown::product.displayModule;
    satisfy 'MRTM-CI-005' by EpbsBreakdown::product.backupAlarmBoard;
    satisfy 'MRTM-CI-006' by EpbsBreakdown::product.batteryPack;
}
