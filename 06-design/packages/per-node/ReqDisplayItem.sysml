package ReqDisplayItem {
    comment /* GENERATED from the Markdown requirement corpus at a7bde1746e07c194.
       Read-only: edit the Markdown requirement, not this file. Sanad regenerates it on
       every corpus change and the same corpus always gives byte-identical text. */

    requirement <'MRTM-DSI-001'> MRTM_DSI_001 {
        doc /* The display item shall redraw the frame within 1 s of a state change message. */
    }

    requirement <'MRTM-DSI-002'> MRTM_DSI_002 {
        doc /* The display item shall change the displayed temperature at most once per 10 s, at 0.1 °C resolution. */
    }
}
