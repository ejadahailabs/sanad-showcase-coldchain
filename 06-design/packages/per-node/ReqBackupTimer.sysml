package ReqBackupTimer {
    comment /* GENERATED from the Markdown requirement corpus at e83adcfc4664281d.
       Read-only: edit the Markdown requirement, not this file. Sanad regenerates it on
       every corpus change and the same corpus always gives byte-identical text. */

    requirement <'MRTM-BKT-001'> MRTM_BKT_001 {
        doc /* The backup timer shall assert its timeout output 9 s ± 0.9 s after the last service pulse. */
    }
}
