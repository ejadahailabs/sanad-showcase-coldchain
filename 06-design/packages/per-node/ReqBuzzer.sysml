package ReqBuzzer {
    comment /* GENERATED from the Markdown requirement corpus at 9d6b4ee0aa229aa9.
       Read-only: edit the Markdown requirement, not this file. Sanad regenerates it on
       every corpus change and the same corpus always gives byte-identical text. */

    requirement <'MRTM-BZR-001'> MRTM_BZR_001 {
        doc /* The buzzer shall produce a sound pressure level of 65 dB(A) or more at 1 m when either drive input is active. */
    }
}
