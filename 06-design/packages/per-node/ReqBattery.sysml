package ReqBattery {
    comment /* GENERATED from the Markdown requirement corpus at 772c8f52f64db9ad.
       Read-only: edit the Markdown requirement, not this file. Sanad regenerates it on
       every corpus change and the same corpus always gives byte-identical text. */

    requirement <'MRTM-BAT-001'> MRTM_BAT_001 {
        doc /* The battery shall store 2000 mAh or more at 3.7 V nominal. */
    }
}
