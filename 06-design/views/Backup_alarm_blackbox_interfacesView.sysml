package Backup_alarm_blackbox_interfacesView {

    comment /* A view file. It imports the packages it draws, exposes elements and names a
       rendering; it declares nothing of the model. Delete it and every package file is
       byte-identical and the model reads unchanged. */

    private import NodeBackupAlarmContext::*;
    private import SanadRenderings::*;

    view 'backup_alarm_blackbox_interfaces' : StandardViewDefinitions::InterconnectionView {
        expose NodeBackupAlarmContext::**;
        render asInterconnectionView;
    }
}

package 'Layout_Sanad' {

    comment /* Layout only. Written and read by this workbench.
       Every entry annotates an element by qualified name; no model element is modified.
       Delete this package and the model is unchanged. */

    private import ScalarValues::*;

    metadata def 'Layout' {
        attribute 'viewName' : String;
        attribute 'x' : Real;
        attribute 'y' : Real;
        attribute 'w' : Real;
        attribute 'h' : Real;
    }

    metadata def 'EdgeLayout' {
        attribute 'viewName' : String;
        attribute 'edge' : String;
        attribute 'bends' : String;
    }

    metadata 'l1' : 'Layout' about 'NodeBackupAlarmContext'::'backupAlarm' {
        'viewName' = "backup_alarm_blackbox_interfaces";
        'x' = 380;
        'y' = 160;
    }

    metadata 'l2' : 'Layout' about 'NodeBackupAlarmContext'::'buzzer' {
        'viewName' = "backup_alarm_blackbox_interfaces";
        'x' = 720;
        'y' = 160;
    }

    metadata 'l3' : 'Layout' about 'NodeBackupAlarmContext'::'power' {
        'viewName' = "backup_alarm_blackbox_interfaces";
        'x' = 40;
        'y' = 290;
    }

    metadata 'l4' : 'Layout' about 'NodeBackupAlarmContext'::'supervision' {
        'viewName' = "backup_alarm_blackbox_interfaces";
        'x' = 40;
        'y' = 40;
    }
}
