// NodeContext — node `context` (context, IEC 62304 class C) of .ejadah/rew/framework.yaml.
// Satisfies ONLY this node's requirements (8). Generated by tools/levels_model.py — edit there. MODEL-LEVELS.
private import ScalarValues::*;
private import ProjectRequirements::*;
private import MrtmInterfaces::*;
private import NodePorts::*;
private import NodeMrtm::*;
private import MrtmSystemContext::*;

package NodeContext {

    doc /* TOP (MagicGrid problem domain): the monitor as ONE box in the clinic, with the people and things it touches. Satisfies the stakeholder requirements only. */

    // Package-level parts so the canvas can place them (F-129). The monitor is ONE box here.
    part fridge : Fridge;
    part monitor : MonitorSystem;
    part mains : MainsSupply;
    part usbHost : UsbHost;
    part staff : Staff;
    interface airContact : ThermalContact connect fridge.air to monitor.air;
    interface mainsFeed : PowerFeed connect mains.output to monitor.mains;
    interface historyLink : UsbLink connect monitor.usb to usbHost.usb;
    connect monitor.alarmSignals to staff.alarmSignals;
    connect monitor.screen to staff.screen;

    satisfy 'MRTM-STK-001' by monitor;
    satisfy 'MRTM-STK-002' by monitor;
    satisfy 'MRTM-STK-003' by monitor;
    satisfy 'MRTM-STK-004' by monitor;
    satisfy 'MRTM-STK-005' by monitor;
    satisfy 'MRTM-STK-006' by monitor;
    satisfy 'MRTM-STK-007' by monitor;
    satisfy 'MRTM-STK-008' by monitor;
}
