// NodeRtc — node `rtc` (hardware-part, IEC 62304 class C) of .ejadah/rew/framework.yaml.
// Covers ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeRtc {

    doc /* LEAF `rtc` (hardware-part). */

    part def Rtc :> MrtmHardware::TcxoRtc {
        doc /* Chosen part: temperature-compensated clock with its own coin cell. */

    }
    part rtc : Rtc;

    satisfy 'MRTM-RTC-001' by rtc;
}
