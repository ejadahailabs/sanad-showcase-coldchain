// NodeUsbItem — node `usb-item` (software-item, IEC 62304 class B) of .ejadah/rew/framework.yaml.
// Covers ONLY this node's requirements (2). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeUsbItem {

    doc /* LEAF `usb-item` (software-item). */

    part def UsbSwItem :> MrtmSoftware::UsbItem {
        doc /* Software item, class B with segregation (IEC 62304 §5.3.5, ADR-0034). Unit: usbExport. */
        port history : ~HistoryFlow;
        port usb : UsbPort;
    }
    part usbSwItem : UsbSwItem;

    satisfy 'MRTM-USI-001' by usbSwItem.usbExport;
    satisfy 'MRTM-USI-002' by usbSwItem.usbExport;
}
