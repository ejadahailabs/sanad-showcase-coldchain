// NodeOled — node `oled` (hardware-part, IEC 62304 class C) of .ejadah/rew/framework.yaml.
// Covers ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeOled {

    doc /* LEAF `oled` (hardware-part). */

    part def Oled :> MrtmHardware::Oled128x64 {
        doc /* Chosen part: 128 × 64 monochrome panel on I2C (ADR-0016). */
        port picture : ScreenPort;
    }
    part oled : Oled;

    satisfy 'MRTM-OLD-001' by oled;
}
