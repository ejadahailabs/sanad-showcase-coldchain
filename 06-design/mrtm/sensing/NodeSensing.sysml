// NodeSensing — node `sensing` (subsystem, IEC 62304 class C) of .ejadah/rew/framework.yaml.
// Covers ONLY this node's requirements (4). Generated by tools/levels_model.py — edit there. MODEL-LEVELS.
private import ScalarValues::*;
private import ProjectRequirements::*;
private import MrtmInterfaces::*;
private import NodePorts::*;
private import MrtmSystemContext::*;
private import NodeProbe::*;
private import NodeSensorItem::*;

package NodeSensing {

    doc /* SENSING subsystem (class C): turns fridge air into one valid-or-invalid sample every 2 s. */

    part def Sensing {
        port air : ~ThermalPort;
        port samples : SampleFlow;
    }

    part def SensingWhiteBox :> Sensing {
        part probe : Probe;
        part sensorItem : SensorSwItem;
        // its wires: package NodeSensingWhiteBox (one file beside this one)
    }
    part sensing : Sensing;

    satisfy 'MRTM-SEN-001' by sensing;
    satisfy 'MRTM-SEN-002' by sensing;
    satisfy 'MRTM-SEN-003' by sensing;
    satisfy 'MRTM-SEN-004' by sensing;
}
