// NodeProbe — node `probe` (hardware-part, IEC 62304 class C) of .ejadah/rew/framework.yaml.
// Covers ONLY this node's requirements (3). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeProbe {

    doc /* LEAF `probe` (hardware-part). */

    part def Probe :> MrtmHardware::Ds18b20 {
        doc /* Chosen part: 1-Wire digital probe on a lead in the fridge air (ADR-0009, ADR-0015). */

    }
    part probe : Probe;

    satisfy 'MRTM-PRB-001' by probe;
    satisfy 'MRTM-PRB-002' by probe;
    satisfy 'MRTM-PRB-003' by probe;
}
