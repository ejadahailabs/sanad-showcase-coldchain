// NodeBuzzer — node `buzzer` (hardware-part, IEC 62304 class C) of .ejadah/rew/framework.yaml.
// Covers ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeBuzzer {

    doc /* LEAF `buzzer` (hardware-part). */

    part def AlarmBuzzer :> MrtmHardware::PiezoBuzzerStage {
        doc /* Chosen part: piezo sounder with two OR-ed drive inputs (ADR-0017). */
        port sound : AlarmHmiPort;
    }
    part alarmBuzzer : AlarmBuzzer;

    satisfy 'MRTM-BZR-001' by alarmBuzzer;
}
