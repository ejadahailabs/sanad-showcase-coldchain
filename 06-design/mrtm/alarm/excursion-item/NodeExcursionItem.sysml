// NodeExcursionItem — node `excursion-item` (software-item, IEC 62304 class C) of .ejadah/rew/framework.yaml.
// Satisfies ONLY this node's requirements (3). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeExcursionItem {

    doc /* LEAF `excursion-item` (software-item). */

    part def ExcursionSwItem :> MrtmSoftware::ExcursionItem {
        doc /* Software item, class C. Unit: limitEvaluator (early, confirmed, end). */
        port samples : ~SampleFlow;
        port excursion : ExcursionFlow;
    }
    part excursionSwItem : ExcursionSwItem;

    satisfy 'MRTM-EXI-001' by excursionSwItem.limitEvaluator;
    satisfy 'MRTM-EXI-002' by excursionSwItem.limitEvaluator;
    satisfy 'MRTM-EXI-003' by excursionSwItem.limitEvaluator;
}
