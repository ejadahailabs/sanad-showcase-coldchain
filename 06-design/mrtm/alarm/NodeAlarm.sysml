// NodeAlarm — node `alarm` (subsystem, IEC 62304 class C) of .ejadah/rew/framework.yaml.
// Satisfies ONLY this node's requirements (8). Generated by tools/levels_model.py — edit there. MODEL-LEVELS.
private import ScalarValues::*;
private import ProjectRequirements::*;
private import MrtmInterfaces::*;
private import NodePorts::*;
private import MrtmSystemContext::*;
private import NodeExcursionItem::*;
private import NodeAlarmItem::*;
private import NodeBuzzer::*;
private import NodeIndicators::*;
private import NodeBackupAlarm::*;

package NodeAlarm {

    doc /* ALARM-AND-INDICATION subsystem (class C): decides the alarm condition and gives the alarm signals (IEC 60601-1-8 frame). The only branch that goes one step deeper (backup alarm). */

    part def Alarm {
        port samples : ~SampleFlow;
        port alarmState : AlarmStateFlow;
        port records : RecordFlow;
        port powerEvents : ~PowerEventFlow;
        port heartbeat : HeartbeatFlow;
        port kick : ~GpioOutPort;
        port supply : ~PowerPort;
        port alarmSignals : AlarmHmiPort;
    }

    part def AlarmWhiteBox :> Alarm {
        part excursionItem : ExcursionSwItem;
        part alarmItem : AlarmSwItem;
        part buzzer : AlarmBuzzer;
        part indicators : Indicators;
        part backupAlarm : BackupAlarmAssembly;
        // its wires: package NodeAlarmWhiteBox (one file beside this one)
    }
    part alarm : Alarm;

    satisfy 'MRTM-ALM-001' by alarm;
    satisfy 'MRTM-ALM-002' by alarm;
    satisfy 'MRTM-ALM-003' by alarm;
    satisfy 'MRTM-ALM-004' by alarm;
    satisfy 'MRTM-ALM-005' by alarm;
    satisfy 'MRTM-ALM-006' by alarm;
    satisfy 'MRTM-ALM-007' by alarm;
    satisfy 'MRTM-ALM-008' by alarm;
}
