// NodeHoldUp — node `hold-up` (hardware-part, IEC 62304 class C) of .ejadah/rew/framework.yaml.
// Covers ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeHoldUp {

    doc /* LEAF `hold-up` (hardware-part). */

    part def HoldUp :> MrtmHardware::Supercap {
        doc /* Chosen part: supercapacitor; 133 s computed hold-up (09-hardware/power-budget.md). */

    }
    part holdUp : HoldUp;

    satisfy 'MRTM-BKH-001' by holdUp;
}
