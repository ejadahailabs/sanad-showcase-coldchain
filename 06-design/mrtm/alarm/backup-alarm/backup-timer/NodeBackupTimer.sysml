// NodeBackupTimer — node `backup-timer` (hardware-part, IEC 62304 class C) of .ejadah/rew/framework.yaml.
// Satisfies ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeBackupTimer {

    doc /* LEAF `backup-timer` (hardware-part). */

    part def BackupTimer :> MrtmHardware::WatchdogAlarmTimer {
        doc /* Chosen part: stand-alone watchdog timer; times out 9 s after the last pulse (EE-REVIEW). */

    }
    part backupTimer : BackupTimer;

    satisfy 'MRTM-BKT-001' by backupTimer;
}
