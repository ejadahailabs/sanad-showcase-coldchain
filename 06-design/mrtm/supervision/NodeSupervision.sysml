// NodeSupervision — node `supervision` (subsystem, IEC 62304 class C) of .ejadah/rew/framework.yaml.
// Covers ONLY this node's requirements (4). Generated by tools/levels_model.py — edit there. MODEL-LEVELS.
private import ScalarValues::*;
private import ProjectRequirements::*;
private import MrtmInterfaces::*;
private import NodePorts::*;
private import MrtmSystemContext::*;
private import NodeMcu::*;
private import NodeSupervisorItem::*;

package NodeSupervision {

    doc /* SUPERVISION subsystem (class C): the processor, its watchdogs, the self-tests and the band check. */

    part def Supervision {
        port heartbeat : ~HeartbeatFlow;
        port kick : GpioOutPort;
        port supply : ~PowerPort;
    }

    part def SupervisionWhiteBox :> Supervision {
        part mcu : Mcu;
        part supervisorItem : SupervisorSwItem;
        // its wires: package NodeSupervisionWhiteBox (one file beside this one)
    }
    part supervision : Supervision;

    satisfy 'MRTM-SUP-001' by supervision;
    satisfy 'MRTM-SUP-002' by supervision;
    satisfy 'MRTM-SUP-003' by supervision;
    satisfy 'MRTM-SUP-004' by supervision;
}
