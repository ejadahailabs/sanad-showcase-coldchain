// NodeSupervisorItem — node `supervisor-item` (software-item, IEC 62304 class C) of .ejadah/rew/framework.yaml.
// Satisfies ONLY this node's requirements (3). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeSupervisorItem {

    doc /* LEAF `supervisor-item` (software-item). */

    part def SupervisorSwItem :> MrtmSoftware::SupervisorItem {
        doc /* Software item, class C. Units: wdtKicker, diagnostics, configMgr. */
        port heartbeat : ~HeartbeatFlow;
        port pulses : GpioOutPort;
    }
    part supervisorSwItem : SupervisorSwItem;

    satisfy 'MRTM-SVI-001' by supervisorSwItem.wdtKicker;
    satisfy 'MRTM-SVI-002' by supervisorSwItem.wdtKicker;
    satisfy 'MRTM-SVI-003' by supervisorSwItem.wdtKicker;
}
