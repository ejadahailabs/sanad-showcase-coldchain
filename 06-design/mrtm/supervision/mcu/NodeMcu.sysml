// NodeMcu — node `mcu` (hardware-part, IEC 62304 class C) of .ejadah/rew/framework.yaml.
// Satisfies ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeMcu {

    doc /* LEAF `mcu` (hardware-part). */

    part def Mcu :> MrtmHardware::Component {
        doc /* Leaf boundary: only the three pins supervision uses. The chosen part (ESP32-S3 class module, A-25) sits inside with all its pins; it hosts every software item. */
        port kickCommand : ~GpioOutPort;
        port wdtKickPin : GpioOutPort;
        port supply : ~PowerPort;
        part module : MrtmHardware::Esp32S3Module;
    }
    part mcu : Mcu;

    satisfy 'MRTM-MCU-001' by mcu;
}
