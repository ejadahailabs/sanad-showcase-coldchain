// NodeMrtm — node `system` (system, IEC 62304 class C) of .ejadah/rew/framework.yaml.
// Satisfies ONLY this node's requirements (62). Generated by tools/levels_model.py — edit there. MODEL-LEVELS.
private import ScalarValues::*;
private import ProjectRequirements::*;
private import MrtmInterfaces::*;
private import NodePorts::*;
private import NodeSensing::*;
private import NodeAlarm::*;
private import NodeDisplay::*;
private import NodeLogging::*;
private import NodePower::*;
private import NodeSupervision::*;

package NodeMrtm {

    doc /* SYSTEM node (IEC 60601-1 PEMS; IEC 62304 software system, class C). Black box: MonitorSystem and its five boundary ports. White box: the six subsystems and their wires. */

    part def MonitorSystem {
        doc /* Black box: what the clinic sees of the monitor. */
        port air : ~ThermalPort;
        port mains : ~PowerPort;
        port usb : UsbPort;
        port alarmSignals : AlarmHmiPort;
        port screen : ScreenPort;
    }
    part def MonitorWhiteBox :> MonitorSystem {
        doc /* White box: six subsystems. Each is a black box of its own one level down. */
        part sensing : Sensing;
        part alarm : Alarm;
        part display : Display;
        part logging : Logging;
        part power : Power;
        part supervision : Supervision;
        // its wires: package NodeSystemWhiteBox (one file beside this one)
    }
    part monitor : MonitorSystem;

    satisfy 'MRTM-ENV-001' by monitor;
    satisfy 'MRTM-ENV-002' by monitor;
    satisfy 'MRTM-ENV-003' by monitor;
    satisfy 'MRTM-ENV-004' by monitor;
    satisfy 'MRTM-IFC-001' by monitor;
    satisfy 'MRTM-IFC-002' by monitor;
    satisfy 'MRTM-IFC-003' by monitor;
    satisfy 'MRTM-IFC-004' by monitor;
    satisfy 'MRTM-MNT-001' by monitor;
    satisfy 'MRTM-MNT-002' by monitor;
    satisfy 'MRTM-MNT-003' by monitor;
    satisfy 'MRTM-PRF-001' by monitor;
    satisfy 'MRTM-PRF-002' by monitor;
    satisfy 'MRTM-PRF-003' by monitor;
    satisfy 'MRTM-PRF-004' by monitor;
    satisfy 'MRTM-SAF-001' by monitor;
    satisfy 'MRTM-SAF-002' by monitor;
    satisfy 'MRTM-SAF-003' by monitor;
    satisfy 'MRTM-SAF-004' by monitor;
    satisfy 'MRTM-SAF-005' by monitor;
    satisfy 'MRTM-SAF-006' by monitor;
    satisfy 'MRTM-SAF-007' by monitor;
    satisfy 'MRTM-SAF-008' by monitor;
    satisfy 'MRTM-SAF-009' by monitor;
    satisfy 'MRTM-SAF-010' by monitor;
    satisfy 'MRTM-SAF-011' by monitor;
    satisfy 'MRTM-SAF-012' by monitor;
    satisfy 'MRTM-SAF-013' by monitor;
    satisfy 'MRTM-SAF-014' by monitor;
    satisfy 'MRTM-SAF-015' by monitor;
    satisfy 'MRTM-SAF-016' by monitor;
    satisfy 'MRTM-SAF-017' by monitor;
    satisfy 'MRTM-SAF-018' by monitor;
    satisfy 'MRTM-SAF-019' by monitor;
    satisfy 'MRTM-SAF-020' by monitor;
    satisfy 'MRTM-SAF-021' by monitor;
    satisfy 'MRTM-SAF-022' by monitor;
    satisfy 'MRTM-SAF-023' by monitor;
    satisfy 'MRTM-SYS-001' by monitor;
    satisfy 'MRTM-SYS-002' by monitor;
    satisfy 'MRTM-SYS-003' by monitor;
    satisfy 'MRTM-SYS-004' by monitor;
    satisfy 'MRTM-SYS-005' by monitor;
    satisfy 'MRTM-SYS-006' by monitor;
    satisfy 'MRTM-SYS-007' by monitor;
    satisfy 'MRTM-SYS-008' by monitor;
    satisfy 'MRTM-SYS-009' by monitor;
    satisfy 'MRTM-SYS-010' by monitor;
    satisfy 'MRTM-SYS-011' by monitor;
    satisfy 'MRTM-SYS-012' by monitor;
    satisfy 'MRTM-SYS-013' by monitor;
    satisfy 'MRTM-SYS-014' by monitor;
    satisfy 'MRTM-SYS-015' by monitor;
    satisfy 'MRTM-SYS-016' by monitor;
    satisfy 'MRTM-SYS-017' by monitor;
    satisfy 'MRTM-SYS-018' by monitor;
    satisfy 'MRTM-SYS-019' by monitor;
    satisfy 'MRTM-SYS-020' by monitor;
    satisfy 'MRTM-SYS-021' by monitor;
    satisfy 'MRTM-SYS-022' by monitor;
    satisfy 'MRTM-SYS-023' by monitor;
    satisfy 'MRTM-SYS-024' by monitor;
}
