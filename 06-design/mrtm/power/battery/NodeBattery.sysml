// NodeBattery — node `battery` (hardware-part, IEC 62304 class C) of .ejadah/rew/framework.yaml.
// Satisfies ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodeBattery {

    doc /* LEAF `battery` (hardware-part). */

    part def MainBattery :> MrtmHardware::LiIonCell {
        doc /* Chosen part: one rechargeable cell (synthetic, A-40). */

    }
    part mainBattery : MainBattery;

    satisfy 'MRTM-BAT-001' by mainBattery;
}
