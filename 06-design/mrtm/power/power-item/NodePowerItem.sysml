// NodePowerItem — node `power-item` (software-item, IEC 62304 class C) of .ejadah/rew/framework.yaml.
// Covers ONLY this node's requirements (2). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodePowerItem {

    doc /* LEAF `power-item` (software-item). */

    part def PowerSwItem :> MrtmSoftware::PowerItem {
        doc /* Software item, class C. Unit: powerMon. */
        port mainsSense : GpioInPort;
        port batterySense : ~PowerPort;
        port events : PowerEventFlow;
        port records : RecordFlow;
    }
    part powerSwItem : PowerSwItem;

    satisfy 'MRTM-PWI-001' by powerSwItem.powerMon;
    satisfy 'MRTM-PWI-002' by powerSwItem.powerMon;
}
