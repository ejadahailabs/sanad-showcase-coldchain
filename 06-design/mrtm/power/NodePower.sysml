// NodePower — node `power` (subsystem, IEC 62304 class C) of .ejadah/rew/framework.yaml.
// Covers ONLY this node's requirements (3). Generated by tools/levels_model.py — edit there. MODEL-LEVELS.
private import ScalarValues::*;
private import ProjectRequirements::*;
private import MrtmInterfaces::*;
private import NodePorts::*;
private import MrtmSystemContext::*;
private import NodeBattery::*;
private import NodePowerPath::*;
private import NodePowerItem::*;

package NodePower {

    doc /* POWER subsystem (class C): mains or battery, switch-over, and the power events. */

    part def Power {
        port mains : ~PowerPort;
        port supply : PowerPort;
        port powerEvents : PowerEventFlow;
        port records : RecordFlow;
    }

    part def PowerWhiteBox :> Power {
        part powerPath : SupplyPath;
        part battery : MainBattery;
        part powerItem : PowerSwItem;
        // its wires: package NodePowerWhiteBox (one file beside this one)
    }
    part power : Power;

    satisfy 'MRTM-PWR-001' by power;
    satisfy 'MRTM-PWR-002' by power;
    satisfy 'MRTM-PWR-003' by power;
}
