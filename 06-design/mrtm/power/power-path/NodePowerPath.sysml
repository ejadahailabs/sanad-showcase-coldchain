// NodePowerPath — node `power-path` (hardware-part, IEC 62304 class C) of .ejadah/rew/framework.yaml.
// Covers ONLY this node's requirements (1). Generated by tools/levels_model.py — edit there. MODEL-LEVELS.
private import ScalarValues::*;
private import ProjectRequirements::*;
private import MrtmInterfaces::*;
private import NodePorts::*;
private import MrtmPhysical::*;
private import MrtmHardware::*;
private import MrtmSoftware::*;

package NodePowerPath {

    doc /* LEAF `power-path` (hardware-part). */

    part def SupplyPath :> MrtmHardware::ChargerPowerPath {
        doc /* Chosen part: charger with automatic change-over to the battery. */

    }
    part supplyPath : SupplyPath;

    satisfy 'MRTM-PPT-001' by supplyPath;
}
